FME workspace postgres2citygml.fmw

Parameters:
- SourceDataset_POSTGRES = 3dcitydblocal   # Connection
- DestDataset_CITYGML = C:\Users\Demo\CesiumCityGMLExp\FME_data_out\citygmltest.gml   # Destination CityGML Document

Readers:
- POSTGRES_1: POSTGRES from $(SourceDataset_POSTGRES)

Writers:
- CITYGML_1: CITYGML to $(DestDataset_CITYGML)

Bookmark: Reader Feature Types
Address (reader POSTGRES_1)
    attributes: gml_id text, gml_parent_id text, citygml_target_uri text, citygml_feature_role text, citygml_feature_role_attr_name text, citygml_feature_role_attr_val text, gml_description text, gml_name text, citygml_address xml
    -> citydb.Address (writer CITYGML_1)
Building (reader POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_class text, citygml_class_codespace text, citygml_function{} text, citygml_function{}_codespace text, citygml_usage{} text, citygml_usage{}_codespace text, citygml_year_of_construction text, citygml_year_of_demolition text, citygml_roof_type text, citygml_roof_type_codespace text, citygml_measured_height float8, citygml_measured_height_units text, citygml_storeys_above_ground numeric(20,0), citygml_storeys_below_ground numeric(20,0),
      citygml_storey_heights_above_ground text, citygml_storey_heights_above_ground_units text, citygml_storey_heights_below_ground text, citygml_storey_heights_below_ground_units text, citygml_outer_building_installation{}_xlink_href text, citygml_interior_building_installation{}_xlink_href text, citygml_bounded_by{}_xlink_href text, citygml_level_of_detail{} text, citygml_interior_room{}_xlink_href text, citygml_consists_of_building_part{}_xlink_href text, citygml_address{}_xlink_href text, brec_buildingheightnn text, brec_roofnames text, buildingheightnn text, code text, c_kayttark text, groundlevel text, highestroof text, id text, i_kerosal text, i_kerrlkm text, kg_krakenn text, katuosoite text, kayttotarkoitus text, kerroksia text, kerrosala text, kokonaisala text, lowestroof text, ratu text, repaired text,
      rakennuksen_tila text, rakennusaine text, rakennustunnus__ratu_ text, rakennustunnus__vtj_prt_ text, roofnames text, suunnitelma_alue text, tila text, tila_koodi text, tyyppi text, tilavuus text, uuid text, vtj_prt text, valmistunut text, bel_spl text, v text, w text, j text, a text
    -> citydb.Building (writer CITYGML_1)
CityModel (reader POSTGRES_1)
    attributes: gml_id text, citygml_target_uri text, gml_description text, gml_name text, citygml_city_object_member{}_xlink_href text, gml_feature_member{}_xlink_href text
    -> citydb.CityModel (writer CITYGML_1)
GroundSurface (reader POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, zmin text, zminasl text
    -> citydb.GroundSurface (writer CITYGML_1)
RoofSurface (reader POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, rooforientation text, roofpitch text, zmax text, zmaxasl text, zmin text, zminasl text
    -> citydb.RoofSurface (writer CITYGML_1)
WallSurface (reader POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, polyareaabs text, polyarearel text, zmax text, zmaxasl text, zmin text, zminasl text
    -> citydb.WallSurface (writer CITYGML_1)

Bookmark: Writer Feature Types
citydb.Address (writer CITYGML_1)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_address xml_xml
citydb.Building (writer CITYGML_1)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_creationdate xml_buffer, citygml_terminationdate xml_buffer, externalreference{}_externalobject_name xml_xml, externalreference{}_externalobject_uri xml_xml, externalreference{}_informationsystem xml_xml, citygml_generalizes_to{}_xlink_href xml_buffer, citygml_relative_to_terrain xml_char(33), citygml_relative_to_water xml_char(38), citygml_class xml_buffer, citygml_class_codespace xml_buffer, citygml_function{} xml_buffer, citygml_function{}_codespace xml_buffer, citygml_usage{} xml_buffer, citygml_usage{}_codespace xml_buffer, citygml_year_of_construction xml_buffer, citygml_year_of_demolition xml_buffer, citygml_roof_type xml_buffer, citygml_roof_type_codespace xml_buffer, citygml_measured_height xml_real64, citygml_measured_height_units xml_buffer, citygml_storeys_above_ground xml_decimal(20,0), citygml_storeys_below_ground xml_decimal(20,0),
      citygml_storey_heights_above_ground xml_buffer, citygml_storey_heights_above_ground_units xml_buffer, citygml_storey_heights_below_ground xml_buffer, citygml_storey_heights_below_ground_units xml_buffer, citygml_outer_building_installation{}_xlink_href xml_buffer, citygml_interior_building_installation{}_xlink_href xml_buffer, citygml_bounded_by{}_xlink_href xml_buffer, citygml_level_of_detail{} xml_buffer, citygml_interior_room{}_xlink_href xml_buffer, citygml_consists_of_building_part{}_xlink_href xml_buffer, citygml_address{}_xlink_href xml_buffer, brec_buildingheightnn xml_buffer, brec_roofnames xml_buffer, buildingheightnn xml_buffer, code xml_buffer, c_kayttark xml_buffer, groundlevel xml_buffer, highestroof xml_buffer, id xml_buffer, i_kerosal xml_buffer, i_kerrlkm xml_buffer, kg_krakenn xml_buffer, katuosoite xml_buffer, kayttotarkoitus xml_buffer, kerroksia xml_buffer, kerrosala xml_buffer, kokonaisala xml_buffer, lowestroof xml_buffer, ratu xml_buffer, repaired xml_buffer,
      rakennuksen_tila xml_buffer, rakennusaine xml_buffer, rakennustunnus__ratu_ xml_buffer, rakennustunnus__vtj_prt_ xml_buffer, roofnames xml_buffer, suunnitelma_alue xml_buffer, tila xml_buffer, tila_koodi xml_buffer, tyyppi xml_buffer, tilavuus xml_buffer, uuid xml_buffer, vtj_prt xml_buffer, valmistunut xml_buffer, bel_spl xml_buffer, v xml_buffer, w xml_buffer, j xml_buffer, a xml_buffer
citydb.CityModel (writer CITYGML_1)
    attributes: gml_id xml_buffer, citygml_target_uri xml_buffer, gml_description xml_buffer, gml_name xml_buffer, citygml_city_object_member{}_xlink_href xml_buffer, gml_feature_member{}_xlink_href xml_buffer
citydb.GroundSurface (writer CITYGML_1)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_creationdate xml_buffer, citygml_terminationdate xml_buffer, externalreference{}_externalobject_name xml_xml, externalreference{}_externalobject_uri xml_xml, externalreference{}_informationsystem xml_xml, citygml_generalizes_to{}_xlink_href xml_buffer, citygml_relative_to_terrain xml_char(33), citygml_relative_to_water xml_char(38), citygml_level_of_detail{} xml_buffer, citygml_opening{}_xlink_href xml_buffer, area xml_buffer, faceuuid xml_buffer, zmin xml_buffer, zminasl xml_buffer
citydb.RoofSurface (writer CITYGML_1)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_creationdate xml_buffer, citygml_terminationdate xml_buffer, externalreference{}_externalobject_name xml_xml, externalreference{}_externalobject_uri xml_xml, externalreference{}_informationsystem xml_xml, citygml_generalizes_to{}_xlink_href xml_buffer, citygml_relative_to_terrain xml_char(33), citygml_relative_to_water xml_char(38), citygml_level_of_detail{} xml_buffer, citygml_opening{}_xlink_href xml_buffer, area xml_buffer, faceuuid xml_buffer, rooforientation xml_buffer, roofpitch xml_buffer, zmax xml_buffer, zmaxasl xml_buffer, zmin xml_buffer, zminasl xml_buffer
citydb.WallSurface (writer CITYGML_1)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_creationdate xml_buffer, citygml_terminationdate xml_buffer, externalreference{}_externalobject_name xml_xml, externalreference{}_externalobject_uri xml_xml, externalreference{}_informationsystem xml_xml, citygml_generalizes_to{}_xlink_href xml_buffer, citygml_relative_to_terrain xml_char(33), citygml_relative_to_water xml_char(38), citygml_level_of_detail{} xml_buffer, citygml_opening{}_xlink_href xml_buffer, area xml_buffer, faceuuid xml_buffer, polyareaabs xml_buffer, polyarearel xml_buffer, zmax xml_buffer, zmaxasl xml_buffer, zmin xml_buffer, zminasl xml_buffer
