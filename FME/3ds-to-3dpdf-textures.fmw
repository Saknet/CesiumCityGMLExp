FME workspace 3ds-to-3dpdf-textures.fmw
Title: 3ds-to-3dpdf-textures

Parameters:
- SourceDataset_3DS = C:\Users\Demo\FME Data In\FME textures exp\City Model\interopolis.3ds   # Source Autodesk 3ds File(s)
- SourceDataset_JPEG = C:\Users\Demo\FME Data In\FME textures exp\City Model\Textures\Roofs\3.jpg   # Source JPEG File(s)
- SourceDataset_JPEG_3 = C:\Users\Demo\FME Data In\FME textures exp\City Model\Textures\Walls\1.jpg   # Source JPEG File(s)
- DestDataset_PDF = C:\Users\Demo\FME Data In\FME textures exp\buildings.pdf   # Destination Adobe 3D PDF File

Readers:
- 3DS_1: 3DS from $(SourceDataset_3DS)
- JPEG_1: JPEG from $(SourceDataset_JPEG)
- JPEG_2: JPEG from $(SourceDataset_JPEG_3)

Writers:
- PDF_1: PDF to $(DestDataset_PDF)

Note: 3DS source Writer
interopolis (reader 3DS_1)
    -> Deaggregator
GeometryExtractor
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
Note: 3D PDF Writer
interopolis (writer PDF_1)
    attributes: 3ds_mesh_name string

Bookmark: Disaggregate mesh to Buildings
Deaggregator
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten One Level
    PART_NUMBER_FIELD = _part_number
    SPLIT_COMPOSITES = Yes
    DEAGGREGATED -> Counter
Counter
    CNT_ATTR = BuildingID
    DOMAIN = counter
    SCOPE = Global
    START = 0
    -> GeometryCoercer

Bookmark: Disaggregate to multisurface
GeometryCoercer
    GQUERY:
      for $geom in //geometry
      where $geom/count(parent::geometry) = 0
      return number($geom/@fme_id)
    KIND = fme_composite_surface
    COERCED -> Deaggregator_2
Note: split incidences and explode
Deaggregator_2
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten One Level
    PART_NUMBER_FIELD = _part_number
    SPLIT_COMPOSITES = Yes
    DEAGGREGATED -> PlanarityFilter

Bookmark: Separate the Roofs from the Walls
PlanarityFilter
    ANGULAR_TOLERANCE_CHOICE = Automatic
    OUTPUT_NORMAL = Yes
    THICKNESS_TOLERANCE_CHOICE = Automatic
    PLANAR -> TestFilter
TestFilter
    DEFAULT_VALUE = Wall
    TEST_LIST:
      "BOOL_OP,OR,COMPOSITE_TEST,""""""<Unused>"""""",TEST_CLAUSE,TEST @Value(_surfaceNormalZ) > 1e-5
      TEST @Value(_surfaceNormalZ) < -1e-5",Roof
    Roof -> AppearanceSetter [GEOMETRY]
    Roof -> GeometryExtractor
    Wall -> AppearanceSetter_2 [GEOMETRY]

Bookmark: Add textures to the roofs and the walls
Note: Wall texture
JPEG (reader JPEG_2)
    -> AppearanceSetter_2 [APPEARANCE]
AppearanceSetter_2
    DEF_STORAGE = Create New Definitions
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator
Note: Roof texture
JPEG (reader JPEG_1)
    -> AppearanceSetter [APPEARANCE]
AppearanceSetter
    DEF_STORAGE = Create New Definitions
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator

Bookmark: Group geometries by BuildingID
Aggregator
    ACCUM_ATTRS_NAME = Use Attributes From One Feature
    AGGREGATE_TYPE = Homogeneous Collection (If Possible)
    GROUP_BY = BuildingID
    MODE = Geometry - Assemble One Level
    ORDERED = No
    SEP = ,
    AGGREGATE -> GeometryCoercer_2
GeometryCoercer_2
    GQUERY:
      for $geom in //geometry
      where $geom/count(parent::geometry) = 0
      return number($geom/@fme_id)
    KIND = fme_composite_surface
    COERCED -> interopolis (writer PDF_1)
