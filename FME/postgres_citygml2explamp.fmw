FME workspace postgres_citygml2explamp.fmw

Parameters:
- SourceDataset_POSTGRES = featureofintrestlocal   # Connection
- DestDataset_CITYGML = C:\Users\Demo\CesiumCityGMLExp\FME_data_out\streetlights.gml   # Destination CityGML Document
- SourceDataset_CITYGML = C:\Users\Demo\FME Data In\KalasatamaPart\TEMP\2549_6674\2549_6674.gml   # Source CityGML File(s)
- SourceDataset_PNGRASTER = $(FME_MF_DIR)datasets\200px-Yellow_icon.png   # Source PNG (Portable Network Graphics) File(s)
- SourceDataset_JPEG = $(FME_MF_DIR)datasets\circle-32.jpg   # Source JPEG File(s)

Readers:
- POSTGRES_1: POSTGRES from $(SourceDataset_POSTGRES)
- CITYGML_1: CITYGML from $(SourceDataset_CITYGML)
- PNGRASTER_1: PNGRASTER from $(SourceDataset_PNGRASTER)
- JPEG_1: JPEG from $(SourceDataset_JPEG)

Writers:
- CITYGML_2: CITYGML to $(DestDataset_CITYGML) in EPSG:3879

FeatureJoiner
    ATTR_CONFLICT_RES = Use Left
    GEOMETRY_HANDLING = Use Left
    JOIN_KEYS = datastream_id id AUTO
    JOIN_MODE = Inner
    JOINED -> FeatureJoiner_2 [LEFT]
FeatureJoiner_2
    ATTR_CONFLICT_RES = Use Left
    GEOMETRY_HANDLING = Use Left
    JOIN_KEYS = thing_link thing_link AUTO
    JOIN_MODE = Inner
    JOINED -> Extract_street_light_data
Extract_street_light_data: JSONExtractor
    EXTRACT_QUERY_TABLE = height json["properties"]["Height"] light_name json["name"] light_description json["description"] lumen json["properties"]["Lumen"]
    JSON_DOCUMENT = @Value(thing_link)
    READ_FROM_FILE = NO
    EVALUATED -> Extract_location_data
Extract_location_data: JSONExtractor
    EXTRACT_QUERY_TABLE = long json["location"]["coordinates"][1] lat json["location"]["coordinates"][0]
    JSON_DOCUMENT = @Value(location_link)
    READ_FROM_FILE = NO
    EVALUATED -> AttributeRenamer
AttributeRenamer
    ATTR_TABLE:
      RENAME_SET_DEFAULT long > x
      RENAME_SET_DEFAULT lat > y
      RENAME_SET_DEFAULT street light height > z
    -> CsmapAttributeReprojector
CsmapAttributeReprojector
    DEST = EPSG:3879
    SOURCE = LL84
    VERTICAL_HANDLING = Heights are relative to the ellipsoid(s) or geocentric
    XATTR = x
    YATTR = y
    ZATTR = height
    REPROJECTED -> Generate_cityfurniture_id
    REPROJECTED -> UUIDGenerator
Generate_cityfurniture_id: UUIDGenerator
    UUID_ATTR = gml_id
    -> StringConcatenator_CityFurnitureID
StringConcatenator_CityFurnitureID
    ACTION = Overwrite Existing Attributes
    ATTRLIST = gml_id
    PARM_LINE = fme_basicstring:16%14:CityFurnitureID_@Value(gml_id)
    -> 2DEllipseReplacer [off]
    -> LampLocation [off]
    -> NW_point_5
LampLocation: VertexCreator
    INDEX = 0
    MEASURE_TYPE = Continuous
    MISSING_VAL_MODE = Compute
    MODE_NAME = Insert Point At Index
    XVAL = @Value(x)
    YVAL = @Value(y)
    ZVAL = @Value(height)
    -> NW_point
    -> NE_point
    -> SE_point
    -> SW_point
    -> AC_CityFurniture_LoD_3
NW_point: VertexCreator
    INDEX = 1
    MEASURE_TYPE = Continuous
    MISSING_VAL_MODE = Compute
    MODE_NAME = Insert Point At Index
    XVAL = @Value(x) - (@Value(height) / 2)
    YVAL = @Value(y) + (@Value(height) / 2)
    ZVAL = 0
    -> NE_point_2
NE_point_2: VertexCreator
    INDEX = 2
    MEASURE_TYPE = Continuous
    MISSING_VAL_MODE = Compute
    MODE_NAME = Insert Point At Index
    XVAL = @Value(x) + (@Value(height) / 2)
    YVAL = @Value(y) + (@Value(height) / 2)
    ZVAL = 0
    -> LampLocation_2
NE_point: VertexCreator
    INDEX = 3
    MEASURE_TYPE = Continuous
    MISSING_VAL_MODE = Compute
    MODE_NAME = Insert Point At Index
    XVAL = @Value(x) + (@Value(height) / 2)
    YVAL = @Value(y) + (@Value(height) / 2)
    ZVAL = 0
    -> SE_point_2
SE_point_2: VertexCreator
    INDEX = 4
    MEASURE_TYPE = Continuous
    MISSING_VAL_MODE = Compute
    MODE_NAME = Insert Point At Index
    XVAL = @Value(x) + (@Value(height) / 2)
    YVAL = @Value(y) - (@Value(height) / 2)
    ZVAL = 0
    -> LampLocation_2
SE_point: VertexCreator
    INDEX = 5
    MEASURE_TYPE = Continuous
    MISSING_VAL_MODE = Compute
    MODE_NAME = Insert Point At Index
    XVAL = @Value(x) + (@Value(height) / 2)
    YVAL = @Value(y) - (@Value(height) / 2)
    ZVAL = 0
    -> SW_point_2
SW_point_2: VertexCreator
    INDEX = 6
    MEASURE_TYPE = Continuous
    MISSING_VAL_MODE = Compute
    MODE_NAME = Insert Point At Index
    XVAL = @Value(x) - (@Value(height) / 2)
    YVAL = @Value(y) - (@Value(height) / 2)
    ZVAL = 0
    -> LampLocation_2
SW_point: VertexCreator
    INDEX = 7
    MEASURE_TYPE = Continuous
    MISSING_VAL_MODE = Compute
    MODE_NAME = Insert Point At Index
    XVAL = @Value(x) - (@Value(height) / 2)
    YVAL = @Value(y) - (@Value(height) / 2)
    ZVAL = 0
    -> NW_point_2
NW_point_2: VertexCreator
    INDEX = 8
    MEASURE_TYPE = Continuous
    MISSING_VAL_MODE = Compute
    MODE_NAME = Insert Point At Index
    XVAL = @Value(x) - (@Value(height) / 2)
    YVAL = @Value(y) + (@Value(height) / 2)
    ZVAL = 0
    -> LampLocation_2
LampLocation_2: VertexCreator
    INDEX = 9
    MEASURE_TYPE = Continuous
    MISSING_VAL_MODE = Compute
    MODE_NAME = Insert Point At Index
    XVAL = @Value(x)
    YVAL = @Value(y)
    ZVAL = @Value(height)
    -> LineBuilder
NW_point_5: VertexCreator
    INDEX = 0
    MEASURE_TYPE = Continuous
    MISSING_VAL_MODE = Compute
    MODE_NAME = Insert Point At Index
    XVAL = @Value(x) - (@Value(height) / 2)
    YVAL = @Value(y) + (@Value(height) / 2)
    ZVAL = 0
    -> NE_point_4
NE_point_4: VertexCreator
    INDEX = 1
    MEASURE_TYPE = Continuous
    MISSING_VAL_MODE = Compute
    MODE_NAME = Insert Point At Index
    XVAL = @Value(x) + (@Value(height) / 2)
    YVAL = @Value(y) + (@Value(height) / 2)
    ZVAL = 0
    -> SE_point_4
SE_point_4: VertexCreator
    INDEX = 2
    MEASURE_TYPE = Continuous
    MISSING_VAL_MODE = Compute
    MODE_NAME = Insert Point At Index
    XVAL = @Value(x) + (@Value(height) / 2)
    YVAL = @Value(y) - (@Value(height) / 2)
    ZVAL = 0
    -> SW_point_4
SW_point_4: VertexCreator
    INDEX = 3
    MEASURE_TYPE = Continuous
    MISSING_VAL_MODE = Compute
    MODE_NAME = Insert Point At Index
    XVAL = @Value(x) - (@Value(height) / 2)
    YVAL = @Value(y) - (@Value(height) / 2)
    ZVAL = 0
    -> NW_point_6
NW_point_6: VertexCreator
    INDEX = 4
    MEASURE_TYPE = Continuous
    MISSING_VAL_MODE = Compute
    MODE_NAME = Insert Point At Index
    XVAL = @Value(x) - (@Value(height) / 2)
    YVAL = @Value(y) + (@Value(height) / 2)
    ZVAL = 0
    -> LineBuilder
LineBuilder
    ACCUM_INPUT_ATTRS = Merge Incoming Attributes
    GROUP_BY = datastream_id
    REMOVE_DUPLICATES = No
    POLYGON -> MinimumSpanningCircleReplacer
MinimumSpanningCircleReplacer
    MODE = Replace Geometry
    RADIUS = _radius
    XCENTER = _center_x
    YCENTER = _center_y
    -> AC_CityFurniture_LoD
AC_CityFurniture_LoD: AttributeCreator
    ATTR_TABLE = SET_TO citygml_lod_name = lod3Geometry
    -> GeometryPropertySetter
GeometryPropertySetter
    OVERWRITE_CHOICE = Yes
    REMOVE_ATTRIBUTE = No
    SETTYPE_PARAM = Traits From Attributes
    SRC_ATTRS = citygml_lod_name
    SET -> CityFurniture (writer CITYGML_2)
    SET -> GeometryExtractor_2
    SET -> EllipsePropertyExtractor
EllipsePropertyExtractor
    CENTER_X = _center_x
    CENTER_Y = _center_y
    CENTER_Z = _center_z
    ORIENTATION = _orientation
    PRIM_RADIUS = _primary_radius
    ROTATION = _rotation
    SEC_RADIUS = _secondary_radius
GeometryExtractor_2
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
CityFurniture (writer CITYGML_2)
    attributes: x xml_char(200), y xml_char(200), id xml_int64, resulttime xml_char(20), result xml_buffer, datastream_id xml_int64, unitofmeasurement xml_buffer, thing_link xml_buffer, location_link xml_buffer, height xml_char(200), name xml_char(200), description xml_char(200), lumen xml_char(200), light_name xml_char(200), light_description xml_char(200), _geometry xml_char(200)
UUIDGenerator
    UUID_ATTR = gml_id
    -> StringConcatenator_CityFurnitureID_2
StringConcatenator_CityFurnitureID_2
    ACTION = Overwrite Existing Attributes
    ATTRLIST = gml_id
    PARM_LINE = fme_basicstring:10%14:LandUseID_@Value(gml_id)
    -> 2DEllipseReplacer
2DEllipseReplacer
    PRIMAXIS = @Value(height) / 2
    ROT = 0
    SECAXIS = @Value(height) / 2
    XVALATTR = @Value(x)
    YVALATTR = @Value(y)
    ELLIPSE -> AC_CityFurniture_LoD_2
    ELLIPSE -> EllipsePropertySetter [off]
AC_CityFurniture_LoD_2: AttributeCreator
    ATTR_TABLE = SET_TO citygml_lod_name = lod3MultiSurface
    -> GeometryPropertySetter_2
GeometryPropertySetter_2
    OVERWRITE_CHOICE = Yes
    REMOVE_ATTRIBUTE = No
    SETTYPE_PARAM = Traits From Attributes
    SRC_ATTRS = citygml_lod_name
    SET -> LandUse (writer CITYGML_2)
    SET -> GeometryExtractor
    SET -> EllipsePropertyExtractor_2
GeometryExtractor
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> LandUse (writer CITYGML_2) [off]
EllipsePropertyExtractor_2
    CENTER_X = _center_x
    CENTER_Y = _center_y
    CENTER_Z = _center_z
    ORIENTATION = _orientation
    PRIM_RADIUS = _primary_radius
    ROTATION = _rotation
    SEC_RADIUS = _secondary_radius
EllipsePropertySetter
    CENTER_X = @Value(x)
    CENTER_Y = @Value(y)
    CENTER_Z = 0
    ORIENTATION_CHOICES = No Change
    PRIM_AXIS = @Value(height)
    SEC_AXIS = @Value(height)
    -> AttributeExposer
    -> LandUse (writer CITYGML_2) [off]
LandUse (writer CITYGML_2)
    attributes: _primary_radius xml_char(200), _secondary_radius xml_char(200), _rotation xml_char(200), _orientation xml_char(200), _center_x xml_char(200), _center_y xml_char(200), _center_z xml_char(200), x xml_char(200), y xml_char(200), id xml_int64, resulttime xml_char(20), result xml_buffer, datastream_id xml_int64, unitofmeasurement xml_buffer, thing_link xml_buffer, location_link xml_buffer, height xml_char(200), light_name xml_char(200), light_description xml_char(200), lumen xml_char(200), _geometry xml_char(200)
AttributeExposer
    ATTR_LIST = fme_geometry
PNGRASTER (reader PNGRASTER_1)
    -> AppearanceSetter [APPEARANCE] [off]
JPEG (reader JPEG_1)
    attributes: comment char(255)
    -> AppearanceSetter [APPEARANCE]
NW_point_3: VertexCreator
    INDEX = 0
    MEASURE_TYPE = Continuous
    MISSING_VAL_MODE = Compute
    MODE_NAME = Insert Point At Index
    XVAL = @Value(x) - (@Value(height) / 2)
    YVAL = @Value(y) + (@Value(height) / 2)
    ZVAL = 0
    -> NE_point_3
NE_point_3: VertexCreator
    INDEX = 1
    MEASURE_TYPE = Continuous
    MISSING_VAL_MODE = Compute
    MODE_NAME = Insert Point At Index
    XVAL = @Value(x) + (@Value(height) / 2)
    YVAL = @Value(y) + (@Value(height) / 2)
    ZVAL = 0
    -> SE_point_3
SE_point_3: VertexCreator
    INDEX = 2
    MEASURE_TYPE = Continuous
    MISSING_VAL_MODE = Compute
    MODE_NAME = Insert Point At Index
    XVAL = @Value(x) + (@Value(height) / 2)
    YVAL = @Value(y) - (@Value(height) / 2)
    ZVAL = 0
    -> SW_point_3
SW_point_3: VertexCreator
    INDEX = 3
    MEASURE_TYPE = Continuous
    MISSING_VAL_MODE = Compute
    MODE_NAME = Insert Point At Index
    XVAL = @Value(x) - (@Value(height) / 2)
    YVAL = @Value(y) - (@Value(height) / 2)
    ZVAL = 0
    -> NW_point_4
NW_point_4: VertexCreator
    INDEX = 4
    MEASURE_TYPE = Continuous
    MISSING_VAL_MODE = Compute
    MODE_NAME = Insert Point At Index
    XVAL = @Value(x) - (@Value(height) / 2)
    YVAL = @Value(y) + (@Value(height) / 2)
    ZVAL = 0
    -> LineBuilder_2
LineBuilder_2
    ACCUM_INPUT_ATTRS = Merge Incoming Attributes
    GROUP_BY = datastream_id
    REMOVE_DUPLICATES = No
    POLYGON -> AC_CityFurniture_LoD_3
AC_CityFurniture_LoD_3: AttributeCreator
    ATTR_TABLE = SET_TO citygml_lod_name = lod1Geometry
    -> GeometryPropertySetter_3
GeometryPropertySetter_3
    OVERWRITE_CHOICE = Yes
    REMOVE_ATTRIBUTE = No
    SETTYPE_PARAM = Traits From Attributes
    SRC_ATTRS = citygml_lod_name
    SET -> GeometryCoercer
GeometryCoercer
    GQUERY:
      for $geom in //geometry
      where $geom/count(parent::geometry) = 0
      return number($geom/@fme_id)
    KIND = fme_polygon
    COERCED -> AppearanceSetter [GEOMETRY]
AppearanceSetter
    DEF_STORAGE = Create New Definitions
    GQUERY:
      for $geom in //geometry
      where $geom/count(parent::geometry) = 0
      return number($geom/@fme_id)
    GROUP_BY = gml_id
    SET_ON_SIDE = Front Side
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> Address (writer CITYGML_2)
Address (writer CITYGML_2)
    attributes: citygml_target_uri xml_buffer, citygml_feature_role xml_buffer, citygml_feature_role_attr_name xml_buffer, citygml_feature_role_attr_val xml_buffer, gml_description xml_buffer, gml_name xml_buffer, citygml_address xml_xml
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, BREC_BuildingHeightNN xml_buffer, BREC_RoofNames xml_buffer, BuildingHeightNN xml_buffer, CODE xml_buffer, C_KAYTTARK xml_buffer, GroundLevel xml_buffer, HighestRoof xml_buffer, ID xml_buffer, I_KEROSAL xml_buffer, I_KERRLKM xml_buffer, KG_KRAKENN xml_buffer, Katuosoite xml_buffer, Kayttotarkoitus xml_buffer, Kerroksia xml_buffer, Kerrosala xml_buffer, Kokonaisala xml_buffer, LowestRoof xml_buffer, RATU xml_buffer, REPAIRED xml_buffer, Rakennuksen_tila xml_buffer, Rakennusaine xml_buffer,
      Rakennustunnus_(RATU) xml_buffer, Rakennustunnus_(VTJ-PRT) xml_buffer, RoofNames xml_buffer, SUUNNITELMA_ALUE xml_buffer, TILA xml_buffer, TILA_KOODI xml_buffer, TYYPPI xml_buffer, Tilavuus xml_buffer, UUID xml_buffer, VTJ_PRT xml_buffer, Valmistunut xml_buffer
    -> Building (writer CITYGML_2)
Building (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, BREC_BuildingHeightNN xml_buffer, BREC_RoofNames xml_buffer, BuildingHeightNN xml_buffer, CODE xml_buffer, C_KAYTTARK xml_buffer, GroundLevel xml_buffer, HighestRoof xml_buffer, ID xml_buffer, I_KEROSAL xml_buffer, I_KERRLKM xml_buffer, KG_KRAKENN xml_buffer, Katuosoite xml_buffer, Kayttotarkoitus xml_buffer, Kerroksia xml_buffer, Kerrosala xml_buffer, Kokonaisala xml_buffer, LowestRoof xml_buffer, RATU xml_buffer, REPAIRED xml_buffer, Rakennuksen_tila xml_buffer, Rakennusaine xml_buffer,
      Rakennustunnus__RATU_ xml_buffer, Rakennustunnus__VTJ-PRT_ xml_buffer, RoofNames xml_buffer, SUUNNITELMA_ALUE xml_buffer, TILA xml_buffer, TILA_KOODI xml_buffer, TYYPPI xml_buffer, Tilavuus xml_buffer, UUID xml_buffer, VTJ_PRT xml_buffer, Valmistunut xml_buffer
CityModel (reader CITYGML_1)
    attributes: citygml_target_uri xml_buffer, gml_description xml_buffer, gml_name xml_buffer, citygml_city_object_member{}.xlink_href xml_buffer, gml_feature_member{}.xlink_href xml_buffer
    -> CityModel (writer CITYGML_2)
CityModel (writer CITYGML_2)
    attributes: citygml_target_uri xml_buffer, gml_description xml_buffer, gml_name xml_buffer, citygml_city_object_member{}.xlink_href xml_buffer, gml_feature_member{}.xlink_href xml_buffer
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, ZMin xml_buffer, ZMinASL xml_buffer
    -> GroundSurface (writer CITYGML_2)
GroundSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, ZMin xml_buffer, ZMinASL xml_buffer
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
    -> RoofSurface (writer CITYGML_2)
RoofSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, PolyAreaAbs xml_buffer, PolyAreaRel xml_buffer, ZMax xml_buffer, ZMaxASL xml_buffer, ZMin xml_buffer, ZMinASL xml_buffer
    -> WallSurface (writer CITYGML_2)
WallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
AuxiliaryTrafficArea (writer CITYGML_2)
    attributes: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
BreaklineRelief (writer CITYGML_2)
    attributes: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
Bridge (writer CITYGML_2)
    attributes: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
BridgeConstructionElement (writer CITYGML_2)
    attributes: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
BridgeFurniture (writer CITYGML_2)
    attributes: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
BridgeInstallation (writer CITYGML_2)
    attributes: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
BridgePart (writer CITYGML_2)
    attributes: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
BridgeRoom (writer CITYGML_2)
    attributes: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
BuildingFurniture (writer CITYGML_2)
    attributes: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
BuildingInstallation (writer CITYGML_2)
    attributes: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
BuildingPart (writer CITYGML_2)
    attributes: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
CeilingSurface (writer CITYGML_2)
    attributes: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
CityObjectGroup (writer CITYGML_2)
    attributes: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
ClosureSurface (writer CITYGML_2)
    attributes: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
Door (writer CITYGML_2)
    attributes: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
FloorSurface (writer CITYGML_2)
    attributes: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
GenericCityObject (writer CITYGML_2)
    attributes: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
HollowSpace (writer CITYGML_2)
    attributes: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
IntBridgeInstallation (writer CITYGML_2)
    attributes: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
IntBuildingInstallation (writer CITYGML_2)
    attributes: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
InteriorWallSurface (writer CITYGML_2)
    attributes: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
IntTunnelInstallation (writer CITYGML_2)
    attributes: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
MassPointRelief (writer CITYGML_2)
    attributes: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
OuterCeilingSurface (writer CITYGML_2)
    attributes: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
OuterFloorSurface (writer CITYGML_2)
    attributes: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
PlantCover (writer CITYGML_2)
    attributes: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
Railway (writer CITYGML_2)
    attributes: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
RasterRelief (writer CITYGML_2)
    attributes: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
ReliefFeature (writer CITYGML_2)
    attributes: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
Road (writer CITYGML_2)
    attributes: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
Room (writer CITYGML_2)
    attributes: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
SolitaryVegetationObject (writer CITYGML_2)
    attributes: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
Square (writer CITYGML_2)
    attributes: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
TINRelief (writer CITYGML_2)
    attributes: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
Track (writer CITYGML_2)
    attributes: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
TrafficArea (writer CITYGML_2)
    attributes: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
TransportationComplex (writer CITYGML_2)
    attributes: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
Tunnel (writer CITYGML_2)
    attributes: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
TunnelFurniture (writer CITYGML_2)
    attributes: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
TunnelInstallation (writer CITYGML_2)
    attributes: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
TunnelPart (writer CITYGML_2)
    attributes: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
WaterBody (writer CITYGML_2)
    attributes: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
WaterClosureSurface (writer CITYGML_2)
    attributes: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
WaterGroundSurface (writer CITYGML_2)
    attributes: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
WaterSurface (writer CITYGML_2)
    attributes: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
Window (writer CITYGML_2)
    attributes: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

Bookmark: Read from database
datastream (reader POSTGRES_1)
    attributes: id int8,PrimaryKey, unitofmeasurement text, thing_link json
    -> FeatureJoiner [RIGHT]
location (reader POSTGRES_1)
    attributes: id int8,PrimaryKey, thing_link json, location_link json
    -> FeatureJoiner_2 [RIGHT]
observation (reader POSTGRES_1)
    attributes: id int8,PrimaryKey, resulttime timestamptz, result text, datastream_id int8
    -> FeatureJoiner [LEFT]
