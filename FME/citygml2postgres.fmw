FME workspace citygml2postgres.fmw

Parameters:
- SourceDataset_CITYGML = C:\Users\Demo\CesiumCityGMLExp\FME_data_in\2549_6674.gml   # Source CityGML File(s)
- DestDataset_POSTGRES = 3dcitydblocal   # Connection

Readers:
- CITYGML_1: CITYGML from $(SourceDataset_CITYGML)

Writers:
- POSTGRES_1: POSTGRES to $(DestDataset_POSTGRES)

AttributeKeeper_2
    CREATE_BULK_MODE_FEATURES = NO
    KEEP_ATTRS = citygml_feature_role_attr_name,citygml_feature_role_attr_val,citygml_target_uri,gml_description,gml_id,gml_name,gml_parent_id
    -> Address (writer POSTGRES_1)
Address (writer POSTGRES_1)
    attributes: citygml_target_uri text, citygml_feature_role_attr_name text, citygml_feature_role_attr_val text, gml_description text, gml_name text, gml_id text, gml_parent_id text
Building (writer POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_class text, citygml_class_codespace text, citygml_function{} text, citygml_function{}_codespace text, citygml_usage{} text, citygml_usage{}_codespace text, citygml_year_of_construction text, citygml_year_of_demolition text, citygml_roof_type text, citygml_roof_type_codespace text, citygml_measured_height float8, citygml_measured_height_units text, citygml_storeys_above_ground numeric(20,0), citygml_storeys_below_ground numeric(20,0),
      citygml_storey_heights_above_ground text, citygml_storey_heights_above_ground_units text, citygml_storey_heights_below_ground text, citygml_storey_heights_below_ground_units text, citygml_outer_building_installation{}_xlink_href text, citygml_interior_building_installation{}_xlink_href text, citygml_bounded_by{}_xlink_href text, citygml_level_of_detail{} text, citygml_interior_room{}_xlink_href text, citygml_consists_of_building_part{}_xlink_href text, citygml_address{}_xlink_href text, brec_buildingheightnn text, brec_roofnames text, buildingheightnn text, code text, c_kayttark text, groundlevel text, highestroof text, id text, i_kerosal text, i_kerrlkm text, kg_krakenn text, katuosoite text, kayttotarkoitus text, kerroksia text, kerrosala text, kokonaisala text, lowestroof text, ratu text, repaired text,
      rakennuksen_tila text, rakennusaine text, rakennustunnus__ratu_ text, rakennustunnus__vtj_prt_ text, roofnames text, suunnitelma_alue text, tila text, tila_koodi text, tyyppi text, tilavuus text, uuid text, vtj_prt text, valmistunut xml
CityModel (writer POSTGRES_1)
    attributes: gml_id text, citygml_target_uri text, gml_description text, gml_name text, citygml_city_object_member{}_xlink_href text, gml_feature_member{}_xlink_href text
GroundSurface (writer POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, zmin text, zminasl text
RoofSurface (writer POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, rooforientation text, roofpitch text, zmax text, zmaxasl text, zmin text, zminasl text
WallSurface (writer POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, polyareaabs text, polyarearel text, zmax text, zmaxasl text, zmin text, zminasl text

Bookmark: Reader Feature Types
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> AttributeKeeper_2
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, BREC_BuildingHeightNN xml_buffer, BREC_RoofNames xml_buffer, BuildingHeightNN xml_buffer, CODE xml_buffer, C_KAYTTARK xml_buffer, GroundLevel xml_buffer, HighestRoof xml_buffer, ID xml_buffer, I_KEROSAL xml_buffer, I_KERRLKM xml_buffer, KG_KRAKENN xml_buffer, Katuosoite xml_buffer, Kayttotarkoitus xml_buffer, Kerroksia xml_buffer, Kerrosala xml_buffer, Kokonaisala xml_buffer, LowestRoof xml_buffer, RATU xml_buffer, REPAIRED xml_buffer, Rakennuksen_tila xml_buffer, Rakennusaine xml_buffer,
      Rakennustunnus_(RATU) xml_buffer, Rakennustunnus_(VTJ-PRT) xml_buffer, RoofNames xml_buffer, SUUNNITELMA_ALUE xml_buffer, TILA xml_buffer, TILA_KOODI xml_buffer, TYYPPI xml_buffer, Tilavuus xml_buffer, UUID xml_buffer, VTJ_PRT xml_buffer, Valmistunut xml_buffer
    -> Building (writer POSTGRES_1)
CityModel (reader CITYGML_1)
    attributes: citygml_target_uri xml_buffer, gml_description xml_buffer, gml_name xml_buffer, citygml_city_object_member{}.xlink_href xml_buffer, gml_feature_member{}.xlink_href xml_buffer
    -> CityModel (writer POSTGRES_1)
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, ZMin xml_buffer, ZMinASL xml_buffer
    -> GroundSurface (writer POSTGRES_1)
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
    -> RoofSurface (writer POSTGRES_1)
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, PolyAreaAbs xml_buffer, PolyAreaRel xml_buffer, ZMax xml_buffer, ZMaxASL xml_buffer, ZMin xml_buffer, ZMinASL xml_buffer
    -> WallSurface (writer POSTGRES_1)
