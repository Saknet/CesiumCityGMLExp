FME workspace kafkatest.fmw

defaultPointMetadata: Creator
    GEOMTYPE = Geometry Object
    NUM = 1
    CREATED -> KafkaConnector
KafkaConnector
    __kafka_action_multiparam = __kafka_topics_list]test.arista.spatineo]__kafka_receive_mode]batch]__kafka_max_messages]<Unused>]__kafka_batch_size]10]__kafka_consumer_group_id]demo-group]__kafka_starting_offset]earliest]__kafka_partition]<Unused>]__kafka_custom_offset]<Unused>]__kafka_auto_commit]YES]__kafka_advanced_options_group]FME_DISCLOSURE_OPEN]__kafka_advanced_options]]__kafka_message_options_group]FME_DISCLOSURE_OPEN]__kafka_message_schema]avro]__kafka_value_encoding]<Unused>]__kafka_schema_registry]https://finest-citygml-exp:dm2mqmiionbkdiin@kafka-28a49ead-fvh-331-datatrials.aivencloud.com:12128]__kafka_attributes_to_add]"_timestamp _topic _value"]FME_CONTROLLER_QUERY_FILE]kafka_deps/Receive.fme
    __kafka_brokers_list = kafka-28a49ead-fvh-331-datatrials.aivencloud.com:12125
    __kafka_connection = finest-citygml-exp
    __kafka_credential_source = webconn
    __kafka_operation_type = Receive
    __kafka_security_protocol = SSL
    __kafka_ssl_ca_location = C:\Users\Demo\Downloads\cerf.ca
    -> AttributeRenamer_3
AttributeRenamer_3
