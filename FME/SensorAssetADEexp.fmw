FME workspace SensorAssetADEexp.fmw

Parameters:
- SourceDataset_CITYGML = C:\Users\Demo\CesiumCityGMLExp\FME_data_in\viikintiedepuisto.gml   # Source CityGML File(s)
- SourceDataset_POSTGRES = db01fvh   # Connection
- DestDataset_CESIUM3DTILES = C:\Users\Demo\CesiumCityGMLExp\public   # Destination Cesium 3D Tiles Folder
- DestDataset_CITYGML = C:\Users\Demo\CesiumCityGMLExp\FME_data_out\testADE.gml   # Destination CityGML Document
- SourceDataset_POSTGRES_3 = db01fvh   # Connection

Readers:
- CITYGML_1: CITYGML from $(SourceDataset_CITYGML)
- POSTGRES_1: POSTGRES from $(SourceDataset_POSTGRES)
- POSTGRES_2: POSTGRES from $(SourceDataset_POSTGRES_3)

Writers:
- CESIUM3DTILES_1: CESIUM3DTILES to $(DestDataset_CESIUM3DTILES)
- CITYGML_2: CITYGML to $(DestDataset_CITYGML)

observation (reader POSTGRES_1)
    attributes: id int8,PrimaryKey, phenomenontime_begin timestamp, phenomenontime_end timestamp, resulttime timestamp, result text, resultquality json, validtime_begin timestamp, validtime_end timestamp, parameters text, datastream_id int8, featureofinterest_id int8, featureofintrest_link text
    -> Observation_tester
Observation_tester: Tester
    BOOL_OP = AND
    COMPOSITE_TEST = 1 AND 2 AND 3 AND 4 AND 5 AND 6 AND 7 AND 8
    TEST_CLAUSE:
      TEST result ATTRIBUTE_HAS_A_VALUE ""
      TEST @Value(result) != 0.0
      TEST @Value(result) != 0
      TEST @Value(result) != false
      TEST @Value(datastream_id) > 0
      TEST featureofinterest_id NOT_ATTRIBUTE_VALUE_NULL ""
      TEST datastream_id NOT_ATTRIBUTE_VALUE_NULL ""
      TEST featureofinterest_id NOT_ATTRIBUTE_IS_MISSING ""
    TEST_MODE = TEST
    PASSED -> AttributeRenamer
AttributeRenamer
    ATTR_TABLE:
      RENAME_SET_DEFAULT result > value
      RENAME_SET_DEFAULT resulttime > time
    -> FeatureJoiner [RIGHT]
datastream (reader POSTGRES_2)
    attributes: id int8,PrimaryKey, name text, description text, observationtype text, unitofmeasurement text, observedarea text, phenomenontime_begin timestamp, phenomenontime_end timestamp, resulttime_begin timestamp, resulttime_end timestamp, sensor_link text, thing_link text, observedproperty_link text
    -> Datastream_tester_2
Datastream_tester_2: Tester
    BOOL_OP = OR
    COMPOSITE_TEST = 1
    TEST_CLAUSE = CASE_INSENSITIVE_TEST @Value(unitofmeasurement) CONTAINS http://
    TEST_MODE = CASE_INSENSITIVE_TEST
    PASSED -> AttributeRenamer_8
AttributeRenamer_8
    ATTR_TABLE = RENAME_SET_DEFAULT unitofmeasurement > uom
    -> PythonCaller_5
PythonCaller_5
    NEW_ATTRIBUTES = unitofmeasurement_json_link
    PYTHONSOURCE:
      import fme
      import fmeobjects
      # Template Function interface:
      # When using this function, make sure its name is set as the value of
      # the 'Class or Function to Process Features' transformer parameter
      def processFeature(feature):
          unitofmeasurement_json_link= 'http://finto.fi/rest/v1/ucum/data?uri=http%3A%2F%2Furn.fi%2FURN%3ANBN%3Afi%3Aau%3Aucum%3Ar'
          unitofmeasurement_link = feature.getAttribute('uom')
          if (":au:ucum:r" in unitofmeasurement_link):
              unitofmeasurement_link_parts = unitofmeasurement_link.split(":au:ucum:r")
          else:
              unitofmeasurement_link_parts = unitofmeasurement_link.split("page/r")

          unitofmeasurement_json_link += unitofmeasurement_link_parts[-1]
          unitofmeasurement_json_link += '&format=application/ld%2Bjson'

          feature.setAttribute('unitofmeasurement_json_link', unitofmeasurement_json_link)


      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> HTTPCaller_2
HTTPCaller_2
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = @Value(unitofmeasurement_json_link)
    TRANSFER_TIMEOUT_LENGTH = 90
    USE_COOKIES = No
    VERIFY_SSL_CERTIFICATES = Yes
    -> JSONExtractor_2
JSONExtractor_2
    EXTRACT_QUERY_TABLE = graph json["graph"] [*]
    JSON_DOCUMENT = @Value(_response_body)
    READ_FROM_FILE = NO
    EVALUATED -> PythonCaller_4
PythonCaller_4
    HIDE_ATTRIBUTES = _response_body
    NEW_ATTRIBUTES = uom
    PYTHONSOURCE:
      import fme
      import fmeobjects
      import json
      # Template Function interface:
      # When using this function, make sure its name is set as the value of
      # the 'Class or Function to Process Features' transformer parameter
      def processFeature(feature):
          graphstring = feature.getAttribute('graph')
          graphstring = graphstring[1:]
          graphstring = graphstring[:-1]
          graphlist = list(graphstring.split("}{"))
          unitofmeasurement = ""

          for item in graphlist:
              json_string = "{" + item + "}"

              json_item = json.loads(json_string)
              if ('http://urn.fi/URN:NBN:fi:au:ucum:p1' in json_item):
                  unitofmeasurement = json_item.get('http://urn.fi/URN:NBN:fi:au:ucum:p1').get('value')

              if (unitofmeasurement == 'B[SPL]'):
                  unitofmeasurement = 'bel_spl'


          feature.setAttribute('uom', unitofmeasurement.lower())

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Tester_2
Tester_2
    BOOL_OP = OR
    COMPOSITE_TEST = 1
    TEST_CLAUSE = TEST uom ATTRIBUTE_HAS_A_VALUE ""
    TEST_MODE = TEST
    PASSED -> AttributeRenamer_7
AttributeRenamer_7
    ATTR_TABLE:
      RENAME_SET_DEFAULT unitofmeasurement > uom
      RENAME_SET_DEFAULT thing_link > thing
      RENAME_SET_DEFAULT sensor_link > sensor
    -> PythonCaller_6
PythonCaller_6
    HIDE_ATTRIBUTES = _response_body
    NEW_ATTRIBUTES = uom
    PYTHONSOURCE:
      import fme
      import fmeobjects
      import json
      # Template Function interface:
      # When using this function, make sure its name is set as the value of
      # the 'Class or Function to Process Features' transformer parameter
      def processFeature(feature):
          graphstring = feature.getAttribute('graph')
          graphstring = graphstring[1:]
          graphstring = graphstring[:-1]
          graphlist = list(graphstring.split("}{"))
          unitofmeasurement = ""

          for item in graphlist:
              json_string = "{" + item + "}"

              json_item = json.loads(json_string)
              if ('http://urn.fi/URN:NBN:fi:au:ucum:p1' in json_item):
                  unitofmeasurement = json_item.get('http://urn.fi/URN:NBN:fi:au:ucum:p1').get('value')

              if (unitofmeasurement == 'B[SPL]'):
                  unitofmeasurement = 'bel_spl'


          feature.setAttribute('uom', unitofmeasurement.lower())

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Tester_4
Tester_4
    BOOL_OP = OR
    COMPOSITE_TEST = 1
    TEST_CLAUSE = TEST uom ATTRIBUTE_HAS_A_VALUE ""
    TEST_MODE = TEST
    PASSED -> AttributeRemover_6
AttributeRemover_6
    REMOVE_ATTRS = graph,_http_status_code,unitofmeasurement_json_link,phenomenontime_begin,phenomenontime_end
    -> UUIDGenerator_SensorID_2
UUIDGenerator_SensorID_2
    UUID_ATTR = sensor_id
    -> StringConcatenator_SensorID_2
StringConcatenator_SensorID_2
    ACTION = Overwrite Existing Attributes
    ATTRLIST = sensor_id
    PARM_LINE = fme_basicstring:9%17:SensorID_@Value(sensor_id)
    -> UUIDGenerator_TimeseriesTVPID_5
UUIDGenerator_TimeseriesTVPID_5
    UUID_ATTR = timeseriesTVP_id
    -> StringConcatenator_TimeseriesTVPID_4
StringConcatenator_TimeseriesTVPID_4
    ACTION = Overwrite Existing Attributes
    ATTRLIST = timeseriesTVP_id
    PARM_LINE = fme_basicstring:16%24:TimeseriesTVPID_@Value(timeseriesTVP_id)
    -> FeatureJoiner_2 [LEFT]
    -> AttributeRenamer_11
AttributeRenamer_11
    ATTR_TABLE:
      RENAME_SET_DEFAULT sensor_id > sensorasset_sensor_xlink_href
      RENAME_SET_DEFAULT timeseriesTVP_id > sensorasset_timeseries_xlink_href
    -> FeatureJoiner [LEFT]
FeatureJoiner
    ATTR_CONFLICT_RES = Use Left
    GEOMETRY_HANDLING = Use Left
    JOIN_KEYS = id datastream_id AUTO
    JOIN_MODE = Inner
    JOINED -> AttributeRemover_11
    JOINED -> DuplicateFilter
    JOINED -> Sampler
Sampler
    GROUP_BY = sensorasset_sensor_xlink_href
    RATE = 1
    SAMPLE_MODE = No
    SAMPLE_TYPE_LONG = First N Features
    SAMPLED -> JSONTemplater_4 [ROOT]
    NOT_SAMPLED -> JSONTemplater_4 [TIMESERIES]
JSONTemplater_4
    CONSECUTIVE_GROUPS = No
    GROUP_BY = sensorasset_sensor_xlink_href
    RESULT_ATTRIBUTE = _result
    ROOT_QUERY_EXPR:
      {
          "sensor" : fme:get-attribute("sensorasset_sensor_xlink_href"),
          "timeseries" : [
              fme:process-features("TIMESERIES")
          ]
      }
    TIMESERIES_QUERY_EXPR:
      {
          "time" : fme:get-attribute("time"),
          "value" : fme:get-attribute("value")
      }
    VISIBLE_QUERY_VALIDATE = Yes
    -> JSONFormatter_3
JSONFormatter_3
    ERROR_LIST_ATTR = _json_error
    FORMAT = Pretty Print
    INDENT_STYLE = 3 spaces
    JSON_DOCUMENT = @Value(_result)
    OUTPUT_ATTR = sensordata
    OUTPUT_ENCODING = UTF-8
    READ_FROM_FILE = NO
    REMOVE_EMPTY_OBJECTS_AND_ARRAYS = No
    REMOVE_EMPTY_STRINGS = No
    REMOVE_NULLS = No
    -> AttributeRemover_7
AttributeRemover_7
    REMOVE_ATTRS = datastream_id,featureofinterest_id,featureofintrest_link,id,name,observationtype,observedarea,observedproperty_link,parameters,phenomenontime_begin,phenomenontime_end,resultquality,resulttime_begin,resulttime_end,sensor,thing,validtime_begin,validtime_end,description,time,uom,value,_result
    -> FeatureJoiner_4 [RIGHT]
DuplicateFilter
    INPUT_ORDERED_CHOICE = No
    KEYATTR = datastream_id
    UNIQUE -> FeatureJoiner_2 [RIGHT]
FeatureJoiner_2
    ATTR_CONFLICT_RES = Use Left
    GEOMETRY_HANDLING = Use Left
    JOIN_KEYS = id datastream_id AUTO
    JOIN_MODE = Inner
    JOINED -> FeatureJoiner_3 [LEFT]
AttributeRemover_11
    REMOVE_ATTRS = datastream_id,description,featureofinterest_id,featureofintrest_link,id,name,observationtype,observedarea,observedproperty_link,parameters,phenomenontime_begin,phenomenontime_end,resultquality,resulttime_begin,resulttime_end,sensor,sensorasset_sensor_xlink_href,thing,validtime_begin,validtime_end,uom
    -> UUIDGenerator_TimeValuePairID_2
UUIDGenerator_TimeValuePairID_2
    UUID_ATTR = gml_id
    -> StringConcatenator_TimeValuePairID_2
StringConcatenator_TimeValuePairID_2
    ACTION = Overwrite Existing Attributes
    ATTRLIST = gml_id
    PARM_LINE = fme_basicstring:16%14:TimeValuePairID_@Value(gml_id)
    -> TimeValuePair (writer CITYGML_2)
featureofinterest (reader POSTGRES_2)
    attributes: id int8,PrimaryKey, name text, description text, encodingtype text, feature text
    -> Extract_location_data
Extract_location_data: JSONExtractor
    EXTRACT_QUERY_TABLE = y json["geometry"]["coordinates"][0] x json["geometry"]["coordinates"][1] latitude json["geometry"]["coordinates"][0] longitude json["geometry"]["coordinates"][1]
    JSON_DOCUMENT = @Value(feature)
    READ_FROM_FILE = NO
    EVALUATED -> CsmapAttributeReprojector
AttributeCreator
    ATTR_TABLE:
      SET_TO latitude = 60.225009
      SET_TO longitude = 25.015681
    -> Create_UnitOfMeasurement_column
Create_UnitOfMeasurement_column: AttributeCreator
    ATTR_TABLE = SET_TO @Value(uom) = @Value(value)
    -> CsmapAttributeReprojector
CsmapAttributeReprojector
    DEST = EPSG:3879
    SOURCE = LL84
    VERTICAL_HANDLING = Ignore heights and leave them unchanged
    XATTR = x
    YATTR = y
    REPROJECTED -> Feature_location
Feature_location: VertexCreator
    MEASURE_TYPE = Continuous
    MISSING_VAL_MODE = Compute
    MODE_NAME = Add Point
    XVAL = @Value(x)
    YVAL = @Value(y)
    -> NeighborFinder [BASE]
GeometryExtractor
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = Yes
    -> AttributeSplitter
AttributeSplitter
    ATTR_NAME = _geometry
    DELIMITER = <gml:surfaceMember>
    DROP_EMPTY_PARTS = No
    LIST_NAME = test
    TRIM_OPTION = None
    -> AttributeSplitter_2
AttributeSplitter_2
    ATTR_NAME = test{1}
    DELIMITER = </gml:surfaceMember>
    DROP_EMPTY_PARTS = No
    LIST_NAME = jee
    TRIM_OPTION = None
    -> AttributeRenamer_3
AttributeRenamer_3
    ATTR_TABLE = RENAME_SET_DEFAULT jee{0} > _geometry
    -> GeometryReplacer
    -> StringReplacer [off]
StringReplacer
    CASE = YES
    FIND_TEXT = FME_CONDITIONAL:DEFAULT_VALUE''BOOL_OP;OR;COMPOSITE_TEST;1;CASE_SENSITIVE_TEST @Value(_geometry) CONTAINS  1.' 1.'BOOL_OP;OR;COMPOSITE_TEST;1;CASE_INSENSITIVE_TEST @Value(_geometry) CONTAINS  2.' 2.'BOOL_OP;OR;COMPOSITE_TEST;1;CASE_INSENSITIVE_TEST @Value(_geometry) CONTAINS  3.' 3.'BOOL_OP;OR;COMPOSITE_TEST;1;CASE_INSENSITIVE_TEST @Value(_geometry) CONTAINS  4.' 4.'BOOL_OP;OR;COMPOSITE_TEST;1;CASE_INSENSITIVE_TEST @Value(_geometry) CONTAINS  5.' 5.'BOOL_OP;OR;COMPOSITE_TEST;1;CASE_INSENSITIVE_TEST @Value(_geometry) CONTAINS  6.' 6.'BOOL_OP;OR;COMPOSITE_TEST;1;CASE_INSENSITIVE_TEST @Value(_geometry) CONTAINS  7.' 7.'BOOL_OP;OR;COMPOSITE_TEST;1;CASE_INSENSITIVE_TEST @Value(_geometry) CONTAINS  8.' 8.'BOOL_OP;OR;COMPOSITE_TEST;1;CASE_INSENSITIVE_TEST @Value(_geometry) CONTAINS  9.' 9.'FME_NUM_CONDITIONS10___
    NO_MATCH = _FME_NO_OP_
    REGEXP = NO
    REPLACE_TEXT = " 0.00"
    SRC_ATTRS = _geometry
    -> GeometryReplacer [off]
GeometryReplacer
    KIND_LONG = GML
    REMOVE_ATTRIBUTE = Yes
    SOURCE = @Value(_geometry)
    SRS_AXIS_ORDER_DISPLAY = Automatic
    -> NeighborFinder [CANDIDATE]
NeighborFinder
    CANDIDATES_FIRST = No
    CLOSE_LIST_ATTRS_TO_INCLUDE = gml_parent_id
    CLOSE_LIST_ATTRS_TO_INCLUDE_MODE = Selected Attributes
    CLOSE_LIST_NAME = closest
    INSERT_VERTEX = No
    K = 1
    MAX = 10
    MEASURES_FROM_CANDIDATE = No
    MEASURE_TYPE = Discrete
    MODE = Bases and Candidates
    TREAT_POLYGON_AS = Areas
    MATCHED -> FeatureJoiner_3 [RIGHT]
FeatureJoiner_3
    ATTR_CONFLICT_RES = Use Left
    GEOMETRY_HANDLING = Use Left
    JOIN_KEYS = featureofinterest_id id AUTO
    JOIN_MODE = Inner
    JOINED -> Feature_location_2
    JOINED -> AttributeRenamer_10
    JOINED -> AttributeRemover_10
    JOINED -> AttributeRemover_9
AttributeRenamer_10
    ATTR_TABLE:
      RENAME_SET_DEFAULT sensor_id > gml_id
      RENAME_SET_DEFAULT closest{0}.gml_parent_id > sensorasset_located_xlink_href
    -> AttributeRemover_4
AttributeRemover_4
    LIST_ATTRS = closest{} closest{}.angle closest{}.candidate_angle closest{}.candidate_label_angle closest{}.closest_base_x closest{}.closest_base_y closest{}.closest_candidate_x closest{}.closest_candidate_y closest{}.distance closest{}.gml_parent_id
    REMOVE_ATTRS = _angle,_candidate_angle,_candidate_label_angle,_closest_base_x,_closest_base_y,_closest_candidate_x,_distance,_closest_candidate_y,datastream_id,encodingtype,feature,featureofinterest_id,featureofintrest_link,id,name,time,validtime_begin,validtime_end,value,sensor,observationtype,observedarea,observedproperty_link,parameters,phenomenontime_begin,phenomenontime_end,resultquality,resulttime_begin,resulttime_end,thing,latitude,longitude,x,y
    -> FeatureJoiner_4 [LEFT]
    -> AttributeRemover_5
FeatureJoiner_4
    ATTR_CONFLICT_RES = Use Left
    GEOMETRY_HANDLING = Use Left
    JOIN_KEYS = gml_id sensorasset_sensor_xlink_href AUTO
    JOIN_MODE = Inner
    JOINED -> Sampler_2
Sampler_2
    GROUP_BY = sensorasset_located_xlink_href
    RATE = 1
    SAMPLE_MODE = No
    SAMPLE_TYPE_LONG = First N Features
    SAMPLED -> JSONTemplater_5 [ROOT]
    NOT_SAMPLED -> JSONTemplater_5 [SENSORS]
JSONTemplater_5
    CONSECUTIVE_GROUPS = No
    GROUP_BY = sensorasset_located_xlink_href
    RESULT_ATTRIBUTE = sensorasset
    ROOT_QUERY_EXPR:
      {
          "sensors" : [
              fme:process-features("SENSORS")
          ]
      }
    SENSORS_QUERY_EXPR:
      {
          "thing-sensor" : fme:get-attribute("description"),
          "uom" : fme:get-attribute("uom"),
          "sensordata" : fme:get-attribute ("sensordata")
      }
    VISIBLE_QUERY_VALIDATE = Yes
    -> AttributeRemover_8
AttributeRemover_8
    REMOVE_ATTRS = description,sensorasset_sensor_xlink_href,sensordata,gml_id,uom
    -> FeatureJoiner_5 [RIGHT]
AttributeRemover_5
    LIST_ATTRS = closest{} closest{}.angle closest{}.candidate_angle closest{}.candidate_label_angle closest{}.closest_base_x closest{}.closest_base_y closest{}.closest_candidate_x closest{}.closest_candidate_y closest{}.distance closest{}.gml_parent_id
    REMOVE_ATTRS = timeseriesTVP_id,uom,sensorasset_timeseries_xlink_href,sensorasset_sensor_xlink_href
    -> Sensor (writer CITYGML_2)
Feature_location_2: VertexCreator
    MEASURE_TYPE = Continuous
    MISSING_VAL_MODE = Compute
    MODE_NAME = Add Point
    XVAL = @Value(x)
    YVAL = @Value(y)
    -> AttributeRemover_2
AttributeRemover_2
    LIST_ATTRS = closest{} closest{}.angle closest{}.candidate_angle closest{}.candidate_label_angle closest{}.closest_base_x closest{}.closest_base_y closest{}.closest_candidate_x closest{}.closest_candidate_y closest{}.distance closest{}.gml_parent_id
    REMOVE_ATTRS = _angle,_candidate_angle,_candidate_label_angle,_closest_base_x,_closest_base_y,_closest_candidate_x,_distance,_closest_candidate_y,datastream_id,encodingtype,feature,featureofinterest_id,featureofintrest_link,id,name,time,uom,validtime_begin,validtime_end,value,sensor,observationtype,observedarea,observedproperty_link,parameters,phenomenontime_begin,phenomenontime_end,resultquality,resulttime_begin,resulttime_end,thing
    -> AC_Location_LoD
AC_Location_LoD: AttributeCreator
    ATTR_TABLE:
      SET_TO citygml_lod_name = realization
      SET_TO citygml_feature_role = locationMember
    -> GeometryPropertySetter
GeometryPropertySetter
    OVERWRITE_CHOICE = Yes
    REMOVE_ATTRIBUTE = No
    SETTYPE_PARAM = Traits From Attributes
    SRC_ATTRS = citygml_lod_name
    SET -> AttributeRenamer_2
AttributeRenamer_2
    ATTR_TABLE = RENAME_SET_DEFAULT sensor_id > sensorasset_sensor_xlink_href
    -> UUIDGenerator_TimeseriesID_4
UUIDGenerator_TimeseriesID_4
    UUID_ATTR = gml_id
    -> StringConcatenator_SensorID_3
StringConcatenator_SensorID_3
    ACTION = Overwrite Existing Attributes
    ATTRLIST = gml_id
    PARM_LINE = fme_basicstring:11%14:LocationID_@Value(gml_id)
    -> AttributeRemover_3
AttributeRemover_3
    REMOVE_ATTRS = timeseriesTVP_id,sensorasset_timeseries_xlink_href,x,y
    -> Location (writer CITYGML_2)
AttributeRemover_10
    LIST_ATTRS = closest{} closest{}.angle closest{}.candidate_angle closest{}.candidate_label_angle closest{}.closest_base_x closest{}.closest_base_y closest{}.closest_candidate_x closest{}.closest_candidate_y closest{}.distance closest{}.gml_parent_id
    REMOVE_ATTRS = _candidate_angle,_candidate_label_angle,_closest_base_x,_closest_base_y,_closest_candidate_x,_closest_candidate_y,_distance,datastream_id,encodingtype,feature,featureofinterest_id,featureofintrest_link,id,latitude,longitude,name,observationtype,observedarea,observedproperty_link,parameters,phenomenontime_begin,phenomenontime_end,resultquality,resulttime_begin,resulttime_end,sensor,sensor_id,thing,time,validtime_begin,validtime_end,value,x,y,_angle,sensorasset_timeseries_xlink_href,uom,description
    -> AttributeRenamer_13
AttributeRenamer_13
    ATTR_TABLE = RENAME_SET_DEFAULT timeseriesTVP_id > gml_id
    -> TimeseriesTVP (writer CITYGML_2)
AttributeRemover_9
    LIST_ATTRS = closest{} closest{}.angle closest{}.candidate_angle closest{}.candidate_label_angle closest{}.closest_base_x closest{}.closest_base_y closest{}.closest_candidate_x closest{}.closest_candidate_y closest{}.distance closest{}.gml_parent_id
    REMOVE_ATTRS = _candidate_angle,_candidate_label_angle,_closest_base_x,_closest_base_y,_closest_candidate_x,_closest_candidate_y,_distance,datastream_id,description,encodingtype,feature,featureofinterest_id,featureofintrest_link,id,latitude,longitude,name,observationtype,observedarea,observedproperty_link,parameters,phenomenontime_begin,phenomenontime_end,resultquality,resulttime_begin,resulttime_end,sensor,sensor_id,sensorasset_sensor_xlink_href,thing,time,validtime_begin,validtime_end,value,x,y,_angle,timeseriesTVP_id
    -> UUIDGenerator_PointMetadataID_3
UUIDGenerator_PointMetadataID_3
    UUID_ATTR = gml_id
    -> StringConcatenator_PointMetadataID_4
StringConcatenator_PointMetadataID_4
    ACTION = Overwrite Existing Attributes
    ATTRLIST = gml_id
    PARM_LINE = fme_basicstring:16%14:PointMetadataID_@Value(gml_id)
    -> PointMetadata (writer CITYGML_2)
FeatureJoiner_5
    ATTR_CONFLICT_RES = Use Left
    GEOMETRY_HANDLING = Use Left
    JOIN_KEYS = gml_id sensorasset_located_xlink_href AUTO
    JOIN_MODE = Inner
    JOINED -> Building (writer CESIUM3DTILES_1)
    UNJOINED_LEFT -> Building (writer CESIUM3DTILES_1)
Building (writer CESIUM3DTILES_1)
    attributes: gml_id string, gml_parent_id string, citygml_target_uri string, citygml_feature_role string, citygml_feature_role_attr_name string, citygml_feature_role_attr_val string, gml_description string, gml_name string, citygml_creationDate string, citygml_terminationDate string, externalReference{}.externalObject.name string, externalReference{}.externalObject.uri string, externalReference{}.informationSystem string, citygml_generalizes_to{}.xlink_href string, citygml_relative_to_terrain string, citygml_relative_to_water string, citygml_class string, citygml_class_codeSpace string, citygml_function{} string, citygml_function{}.codeSpace string, citygml_usage{} string, citygml_usage{}.codeSpace string, citygml_year_of_construction string, citygml_year_of_demolition string, citygml_roof_type string, citygml_roof_type_codeSpace string, citygml_measured_height float, citygml_measured_height_units string, citygml_storeys_above_ground string, citygml_storeys_below_ground string,
      citygml_storey_heights_above_ground string, citygml_storey_heights_above_ground_units string, citygml_storey_heights_below_ground string, citygml_storey_heights_below_ground_units string, citygml_outer_building_installation{}.xlink_href string, citygml_interior_building_installation{}.xlink_href string, citygml_bounded_by{}.xlink_href string, citygml_level_of_detail{} string, citygml_interior_room{}.xlink_href string, citygml_consists_of_building_part{}.xlink_href string, citygml_address{}.xlink_href string, BREC_BuildingHeightNN string, BREC_RoofNames string, BuildingHeightNN string, CODE string, C_KAYTTARK string, GroundLevel string, HighestRoof string, ID string, I_KEROSAL string, I_KERRLKM string, KG_KRAKENN string, Katuosoite string, Kayttotarkoitus string, Kerroksia string, Kerrosala string, Kokonaisala string, LowestRoof string, RATU string, REPAIRED string,
      Rakennuksen_tila string, Rakennusaine string, Rakennustunnus_(RATU) string, Rakennustunnus_(VTJ-PRT) string, RoofNames string, SUUNNITELMA_ALUE string, TILA string, TILA_KOODI string, TYYPPI string, Tilavuus string, UUID string, VTJ_PRT string, Valmistunut string, citygml_city_object_member{}.xlink_href string, gml_feature_member{}.xlink_href string, citygml_opening{}.xlink_href string, Area string, FaceUUID string, RoofOrientation string, RoofPitch string, ZMax string, ZMaxASL string, ZMin string, ZMinASL string, datastream_id int, point{}.value string, point{}.time string, latitude string, longitude string, pointMetadata{}.uom string,
      TimeseriesTVP{}.point{}.value string, TimeseriesTVP{}.point{}.time string, TimeseriesTVP{}.pointMetadata{}.uom string, Location{}.latitude string, Location{}.longitude string, Sensor{}.sensor_link string, Sensor{}.thing_link string, Sensor{}.TimeseriesTVP{}.point{}.value string, Sensor{}.TimeseriesTVP{}.point{}.time string, Sensor{}.TimeseriesTVP{}.pointMetadata{}.uom string, Sensor{}.Location{}.latitude string, Sensor{}.Location{}.longitude string, uom string, value string, time string, id int, validtime_begin string, validtime_end string, featureofinterest_id int, featureofintrest_link string, sensor_link string, thing_link string, description string, encodingtype string, feature string, name string, _matched_records string, closest{}.gml_parent_id string, _distance string, _angle string,
      _candidate_angle string, _candidate_label_angle string, _closest_candidate_x string, _closest_candidate_y string, _closest_base_x string, _closest_base_y string, closest{}.distance string, closest{}.angle string, closest{}.candidate_angle string, closest{}.candidate_label_angle string, closest{}.closest_candidate_x string, closest{}.closest_candidate_y string, closest{}.closest_base_x string, closest{}.closest_base_y string, _relationships{}.gml_parent_id string, _relationships{}.de9im string, _relationships{}.pass{} string, _relationships{}.card_point string, _relationships{}.card_line string, _relationships{}.card_area string, _related_candidates string, matched{}.gml_parent_id string, observations{}.uom string, observations{}.value string, observations{}.time string, observations{}.sensor_link string, observations{}.thing_link string, citygml_address string, PolyAreaAbs string, PolyAreaRel string,
      Sensor{}.sensor string, sensors json, sensorasset json
AttributeRenamer_4
    ATTR_TABLE = RENAME_SET_DEFAULT sensorasset_timeseries_xlink_href > gml_parent_id
    -> TimeValuePair (writer CITYGML_2) [off]

Bookmark: Reader Feature Types
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, PolyAreaAbs xml_buffer, PolyAreaRel xml_buffer, ZMax xml_buffer, ZMaxASL xml_buffer, ZMin xml_buffer, ZMinASL xml_buffer
    -> WallSurface (writer CITYGML_2)
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
    -> GeometryExtractor
    -> RoofSurface (writer CITYGML_2)
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, ZMin xml_buffer, ZMinASL xml_buffer
    -> GeometryExtractor [off]
    -> GroundSurface (writer CITYGML_2)
CityModel (reader CITYGML_1)
    attributes: citygml_target_uri xml_buffer, gml_description xml_buffer, gml_name xml_buffer, citygml_city_object_member{}.xlink_href xml_buffer, gml_feature_member{}.xlink_href xml_buffer
    -> CityModel (writer CITYGML_2)
    -> Building (writer CESIUM3DTILES_1)
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, BREC_BuildingHeightNN xml_buffer, BREC_RoofNames xml_buffer, BuildingHeightNN xml_buffer, CODE xml_buffer, C_KAYTTARK xml_buffer, GroundLevel xml_buffer, HighestRoof xml_buffer, ID xml_buffer, I_KEROSAL xml_buffer, I_KERRLKM xml_buffer, KG_KRAKENN xml_buffer, Katuosoite xml_buffer, Kayttotarkoitus xml_buffer, Kerroksia xml_buffer, Kerrosala xml_buffer, Kokonaisala xml_buffer, LowestRoof xml_buffer, RATU xml_buffer, REPAIRED xml_buffer, Rakennuksen_tila xml_buffer, Rakennusaine xml_buffer,
      Rakennustunnus_(RATU) xml_buffer, Rakennustunnus_(VTJ-PRT) xml_buffer, RoofNames xml_buffer, SUUNNITELMA_ALUE xml_buffer, TILA xml_buffer, TILA_KOODI xml_buffer, TYYPPI xml_buffer, Tilavuus xml_buffer, UUID xml_buffer, VTJ_PRT xml_buffer, Valmistunut xml_buffer
    -> Building (writer CITYGML_2)
    -> FeatureJoiner_5 [LEFT]
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> Address (writer CITYGML_2)

Bookmark: CityGML Writer
WallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, PolyAreaAbs xml_buffer, PolyAreaRel xml_buffer, ZMax xml_buffer, ZMaxASL xml_buffer, ZMin xml_buffer, ZMinASL xml_buffer
RoofSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
GroundSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, ZMin xml_buffer, ZMinASL xml_buffer
Sensor (writer CITYGML_2)
    attributes: sensorasset_located_xlink_href xml_buffer, description xml_buffer, sensorasset_location_member{}.xlink_href xml_buffer, sensorasset_timeseries_xlink_href xml_buffer
Location (writer CITYGML_2)
    attributes: description xml_char(200), latitude xml_buffer, longitude xml_buffer, citygml_feature_role xml_buffer, sensorasset_sensor_xlink_href xml_buffer
TimeseriesTVP (writer CITYGML_2)
    attributes: sensorasset_sensor_xlink_href xml_buffer, sensorasset_time_value_pair_member{}.xlink_href xml_buffer, sensorasset_default_point_metadata.xlink_href xml_buffer
PointMetadata (writer CITYGML_2)
    attributes: uom xml_buffer, sensorasset_timeseries_xlink_href xml_buffer
CityModel (writer CITYGML_2)
    attributes: citygml_target_uri xml_buffer, gml_description xml_buffer, gml_name xml_buffer, citygml_city_object_member{}.xlink_href xml_buffer, gml_feature_member{}.xlink_href xml_buffer
Building (writer CITYGML_2)
    attributes: BREC_BuildingHeightNN xml_buffer, BREC_RoofNames xml_buffer, BuildingHeightNN xml_buffer, C_KAYTTARK xml_buffer, citygml_address{}.xlink_href xml_buffer, citygml_bounded_by{}.xlink_href xml_buffer, citygml_class xml_buffer, citygml_class_codeSpace xml_buffer, citygml_consists_of_building_part{}.xlink_href xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_interior_building_installation{}.xlink_href xml_buffer, citygml_interior_room{}.xlink_href xml_buffer, citygml_level_of_detail{} xml_buffer, citygml_measured_height xml_real64, citygml_measured_height_units xml_buffer, citygml_outer_building_installation{}.xlink_href xml_buffer, citygml_relative_to_terrain xml_char(33), citygml_relative_to_water xml_char(38), citygml_roof_type xml_buffer, citygml_roof_type_codeSpace xml_buffer, citygml_storey_heights_above_ground xml_buffer, citygml_storey_heights_above_ground_units xml_buffer, citygml_storey_heights_below_ground xml_buffer, citygml_storey_heights_below_ground_units xml_buffer,
      citygml_storeys_above_ground xml_uint64, citygml_storeys_below_ground xml_uint64, citygml_target_uri xml_buffer, citygml_terminationDate xml_date, citygml_usage{} xml_buffer, citygml_usage{}.codeSpace xml_buffer, citygml_year_of_construction xml_buffer, citygml_year_of_demolition xml_buffer, CODE xml_buffer, externalReference{}.externalObject.name xml_xml, externalReference{}.externalObject.uri xml_xml, externalReference{}.informationSystem xml_xml, gml_description xml_buffer, gml_name xml_buffer, GroundLevel xml_buffer, HighestRoof xml_buffer, I_KEROSAL xml_buffer, I_KERRLKM xml_buffer, ID xml_buffer, Katuosoite xml_buffer, Kayttotarkoitus xml_buffer, Kerroksia xml_buffer, Kerrosala xml_buffer, KG_KRAKENN xml_buffer, Kokonaisala xml_buffer, LowestRoof xml_buffer, Rakennuksen_tila xml_buffer, Rakennusaine xml_buffer, Rakennustunnus__RATU_ xml_buffer, Rakennustunnus__VTJ-PRT_ xml_buffer,
      RATU xml_buffer, REPAIRED xml_buffer, RoofNames xml_buffer, sensorasset_sensor{}.xlink_href xml_buffer, SUUNNITELMA_ALUE xml_buffer, TILA xml_buffer, TILA_KOODI xml_buffer, Tilavuus xml_buffer, TYYPPI xml_buffer, UUID xml_buffer, Valmistunut xml_buffer, VTJ_PRT xml_buffer
Address (writer CITYGML_2)
    attributes: citygml_target_uri xml_buffer, citygml_feature_role xml_buffer, citygml_feature_role_attr_name xml_buffer, citygml_feature_role_attr_val xml_buffer, gml_description xml_buffer, gml_name xml_buffer, citygml_address xml_xml
TimeValuePair (writer CITYGML_2)
    attributes: value xml_buffer, time xml_datetime, sensorasset_timeseries_xlink_href xml_buffer
