FME workspace postgres_postgres2json.fmw

Parameters:
- SourceDataset_POSTGRES = db01fvh   # Connection
- DestDataset_JSON = C:\Users\Demo\FME Data out\kalasatamapart\obs.json   # Destination JSON (JavaScript Object Notation) File
- SourceDataset_CITYGML = C:\Users\Demo\CesiumCityGMLExp\FME_data_in\2549_6674.gml   # Source CityGML File(s)
- DestDataset_CITYGML = C:\Users\Demo\CesiumCityGMLExp\FME_data_out\kalasatamapart.gml   # Destination CityGML Document
- DestDataset_JSON_5 = C:\Users\Demo\FME Data out\LDExperiements\ucumtest.json   # Destination JSON (JavaScript Object Notation) File
- SourceDataset_POSTGRES_7 = featureofintrestlocal   # Connection
- SourceDataset_POSTGRES_4 = 3dcitydblocal   # Connection
- DestDataset_POSTGRES = 3dcitydblocal   # Connection
- DestDataset_CITYGML_4 = C:\Users\Demo\CesiumCityGMLExp\FME_data_out\kalasatamapart2.gml   # Destination CityGML Document
- DestDataset_CESIUM3DTILES = C:\Users\Demo\CesiumCityGMLExp\public\Third   # Destination Cesium 3D Tiles Folder

Readers:
- POSTGRES_1: POSTGRES from $(SourceDataset_POSTGRES)
- CITYGML_1: CITYGML from $(SourceDataset_CITYGML)
- POSTGRES_2: POSTGRES from $(SourceDataset_POSTGRES_7)
- POSTGRES_3: POSTGRES from $(SourceDataset_POSTGRES_4)

Writers:
- JSON_1: JSON to $(DestDataset_JSON)
- CITYGML_2: CITYGML to $(DestDataset_CITYGML)
- JSON_2: JSON to $(DestDataset_JSON_5)
- POSTGRES_4: POSTGRES to $(DestDataset_POSTGRES)
- CITYGML_3: CITYGML to $(DestDataset_CITYGML_4)
- CESIUM3DTILES_1: CESIUM3DTILES to $(DestDataset_CESIUM3DTILES)

FeatureOfInterest (reader POSTGRES_2)
    attributes: id int8, linkeddata json, datastream_id int8
    -> JSONExtractor_2
JSONExtractor_2
    EXTRACT_QUERY_TABLE = gml_id json["feature"]
    JSON_DOCUMENT = @Value(linkeddata)
    READ_FROM_FILE = NO
    EVALUATED -> AttributeKeeper_2
AttributeKeeper_2
    CREATE_BULK_MODE_FEATURES = NO
    KEEP_ATTRS = datastream_id,gml_id
    -> FeatureJoiner [RIGHT]
Observation_tester: Tester
    BOOL_OP = COMPOSITE
    COMPOSITE_TEST = 1 AND 2 AND 3 AND 4 AND 5
    TEST_CLAUSE:
      TEST result ATTRIBUTE_HAS_A_VALUE ""
      TEST @Value(result) != 0.0
      TEST @Value(result) != 0
      TEST @Value(result) != false
      TEST @Value(datastream_id) > 0
    TEST_MODE = TEST
    PASSED -> Sorter
Sorter
    SORT_PARM = resulttime NUMERIC DESCENDING
    SORTED -> DuplicateFilter
DuplicateFilter
    INPUT_ORDERED_CHOICE = No
    KEYATTR = datastream_id
    UNIQUE -> DatabaseJoiner
DatabaseJoiner
    ADDED_FIELDS = unitofmeasurement
    ATTR_ACCUM_MODE = Merge Joined
    ATTR_CONFLICT_RES = Use Original
    CACHE_SIZE = 5000
    DATASET = db01fvh
    FORMAT = POSTGRES
    JOIN_KEYS = datastream_id id
    MATCH_MULTIPLE_DISPLAY = Create a feature for each match
    MATCH_RULE_DISPLAY = Match All (1:M)
    POSTGRES_CREATE_FEATURE_TABLES_FROM_DATA = Yes
    POSTGRES_NAMED_CONNECTION = db01fvh
    POSTGRES_QUERY_FEATURE_TYPES_FOR_MERGE_FILTERS = Yes
    POSTGRES_READ_TIME_WITH_TIMEZONE = Yes
    PREFETCH_EXHAUSTIVE = Yes
    PREFETCH_QUERY = select * from "public"."datastream"
    TABLE = public.datastream
    JOINED -> Datastream_tester
Datastream_tester: Tester
    BOOL_OP = OR
    COMPOSITE_TEST = 1
    TEST_CLAUSE = CASE_INSENSITIVE_TEST @Value(unitofmeasurement) CONTAINS http://
    TEST_MODE = CASE_INSENSITIVE_TEST
    PASSED -> FeatureJoiner [LEFT]
FeatureJoiner
    ATTR_CONFLICT_RES = Use Left
    GEOMETRY_HANDLING = Use Left
    JOIN_KEYS = datastream_id datastream_id AUTO
    JOIN_MODE = Inner
    JOINED -> public.observation (writer JSON_1)
    JOINED -> PythonCaller_2
PythonCaller_2
    HIDE_ATTRIBUTES = _response_body
    NEW_ATTRIBUTES = unitofmeasurement_json_link
    PYTHONSOURCE:
      import fme
      import fmeobjects
      # Template Function interface:
      # When using this function, make sure its name is set as the value of
      # the 'Class or Function to Process Features' transformer parameter
      def processFeature(feature):
          unitofmeasurement_json_link= 'http://finto.fi/rest/v1/ucum/data?uri=http%3A%2F%2Furn.fi%2FURN%3ANBN%3Afi%3Aau%3Aucum%3Ar'
          unitofmeasurement_link = feature.getAttribute('unitofmeasurement')
          if (":au:ucum:r" in unitofmeasurement_link):
              unitofmeasurement_link_parts = unitofmeasurement_link.split(":au:ucum:r")
          else:
              unitofmeasurement_link_parts = unitofmeasurement_link.split("page/r")

          unitofmeasurement_json_link += unitofmeasurement_link_parts[-1]
          unitofmeasurement_json_link += '&format=application/ld%2Bjson'

          feature.setAttribute('unitofmeasurement_json_link', unitofmeasurement_json_link)


      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> HTTPCaller
HTTPCaller
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = @Value(unitofmeasurement_json_link)
    TRANSFER_TIMEOUT_LENGTH = 90
    USE_COOKIES = No
    VERIFY_SSL_CERTIFICATES = Yes
    -> AttributeKeeper
AttributeKeeper
    CREATE_BULK_MODE_FEATURES = NO
    KEEP_ATTRS = _response_body,datastream_id,featureofintrest_link,result,resulttime,gml_id
    -> JSONExtractor
JSONExtractor
    EXTRACT_QUERY_TABLE = graph json["graph"] [*]
    JSON_DOCUMENT = @Value(_response_body)
    READ_FROM_FILE = NO
    EVALUATED -> PythonCaller
PythonCaller
    HIDE_ATTRIBUTES = _response_body
    NEW_ATTRIBUTES = unitofmeasurement
    PYTHONSOURCE:
      import fme
      import fmeobjects
      import json
      # Template Function interface:
      # When using this function, make sure its name is set as the value of
      # the 'Class or Function to Process Features' transformer parameter
      def processFeature(feature):
          graphstring = feature.getAttribute('graph')
          graphstring = graphstring[1:]
          graphstring = graphstring[:-1]
          graphlist = list(graphstring.split("}{"))
          unitofmeasurement = ""

          for item in graphlist:
              json_string = "{" + item + "}"

              json_item = json.loads(json_string)
              if ('http://urn.fi/URN:NBN:fi:au:ucum:p1' in json_item):
                  unitofmeasurement = json_item.get('http://urn.fi/URN:NBN:fi:au:ucum:p1').get('value')

              if (unitofmeasurement == 'B[SPL]'):
                  unitofmeasurement = 'bel_spl'


          feature.setAttribute('unitofmeasurement', unitofmeasurement.lower())

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Tester
Tester
    BOOL_OP = OR
    COMPOSITE_TEST = 1
    TEST_CLAUSE = TEST unitofmeasurement ATTRIBUTE_HAS_A_VALUE ""
    TEST_MODE = TEST
    PASSED -> Create_UnitOfMeasurement_column
Create_UnitOfMeasurement_column: AttributeCreator
    ATTR_TABLE = SET_TO @Value(unitofmeasurement) = @Value(result)
    -> AttributeRemover
AttributeRemover
    REMOVE_ATTRS = graph,unitofmeasurement,result
    -> DateTimeStamper
DateTimeStamper
    DATETIME_ATTR = _timestamp
    INCLUDE_OFFSET = YES
    STAMP_TYPE = datetime
    TIMEZONE = local
    -> FeatureMerger [SUPPLIER]
    -> FeatureMerger_2 [SUPPLIER]
Building (reader POSTGRES_3)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_class text, citygml_class_codespace text, citygml_function{} text, citygml_function{}_codespace text, citygml_usage{} text, citygml_usage{}_codespace text, citygml_year_of_construction text, citygml_year_of_demolition text, citygml_roof_type text, citygml_roof_type_codespace text, citygml_measured_height float8, citygml_measured_height_units text, citygml_storeys_above_ground numeric(20,0), citygml_storeys_below_ground numeric(20,0),
      citygml_storey_heights_above_ground text, citygml_storey_heights_above_ground_units text, citygml_storey_heights_below_ground text, citygml_storey_heights_below_ground_units text, citygml_outer_building_installation{}_xlink_href text, citygml_interior_building_installation{}_xlink_href text, citygml_bounded_by{}_xlink_href text, citygml_level_of_detail{} text, citygml_interior_room{}_xlink_href text, citygml_consists_of_building_part{}_xlink_href text, citygml_address{}_xlink_href text, brec_buildingheightnn text, brec_roofnames text, buildingheightnn text, code text, c_kayttark text, groundlevel text, highestroof text, id text, i_kerosal text, i_kerrlkm text, kg_krakenn text, katuosoite text, kayttotarkoitus text, kerroksia text, kerrosala text, kokonaisala text, lowestroof text, ratu text, repaired text,
      rakennuksen_tila text, rakennusaine text, rakennustunnus__ratu_ text, rakennustunnus__vtj_prt_ text, roofnames text, suunnitelma_alue text, tila text, tila_koodi text, tyyppi text, tilavuus text, uuid text, vtj_prt text, valmistunut text, bel_spl text, v text, w text, j text, a text
    -> FeatureMerger [REQUESTOR]
FeatureMerger
    ATTR_ACCUM_MODE = Merge Supplier
    ATTR_CONFLICT_RES = Use Requestor
    CLEANING_TOLERANCE = Automatic
    CONNECT_Z_MODE = Extend
    GEOM_TYPE = Build Polygons
    IGNORE_NULLS = No
    JOIN_KEYS = @Value(gml_id) @Value(gml_id) AUTO
    MERGE_TYPE = Attributes Only
    PROCESS_DUPS = YES
    REJECT_NULL_MISSING_KEYS = No
    SUPPLIERS_FIRST = No
    MERGED -> Building (writer CITYGML_3)
    UNMERGED_REQUESTOR -> Building (writer CITYGML_3)
Building (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
Building (reader CITYGML_1)
    attributes: BREC_BuildingHeightNN xml_buffer, BREC_RoofNames xml_buffer, BuildingHeightNN xml_buffer, C_KAYTTARK xml_buffer, citygml_address{}.xlink_href xml_buffer, citygml_bounded_by{}.xlink_href xml_buffer, citygml_class xml_buffer, citygml_class_codeSpace xml_buffer, citygml_consists_of_building_part{}.xlink_href xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_interior_building_installation{}.xlink_href xml_buffer, citygml_interior_room{}.xlink_href xml_buffer, citygml_level_of_detail{} xml_buffer, citygml_measured_height xml_real64, citygml_measured_height_units xml_buffer, citygml_outer_building_installation{}.xlink_href xml_buffer, citygml_relative_to_terrain xml_char(33), citygml_relative_to_water xml_char(38), citygml_roof_type xml_buffer, citygml_roof_type_codeSpace xml_buffer, citygml_storey_heights_above_ground xml_buffer, citygml_storey_heights_above_ground_units xml_buffer, citygml_storey_heights_below_ground xml_buffer, citygml_storey_heights_below_ground_units xml_buffer,
      citygml_storeys_above_ground xml_uint64, citygml_storeys_below_ground xml_uint64, citygml_target_uri xml_buffer, citygml_terminationDate xml_date, citygml_usage{} xml_buffer, citygml_usage{}.codeSpace xml_buffer, citygml_year_of_construction xml_buffer, citygml_year_of_demolition xml_buffer, CODE xml_buffer, externalReference{}.externalObject.name xml_xml, externalReference{}.externalObject.uri xml_xml, externalReference{}.informationSystem xml_xml, gml_description xml_buffer, gml_name xml_buffer, GroundLevel xml_buffer, HighestRoof xml_buffer, I_KEROSAL xml_buffer, I_KERRLKM xml_buffer, ID xml_buffer, Katuosoite xml_buffer, Kayttotarkoitus xml_buffer, Kerroksia xml_buffer, Kerrosala xml_buffer, KG_KRAKENN xml_buffer, Kokonaisala xml_buffer, LowestRoof xml_buffer, Rakennuksen_tila xml_buffer, Rakennusaine xml_buffer, Rakennustunnus_(RATU) xml_buffer, Rakennustunnus_(VTJ-PRT) xml_buffer,
      RATU xml_buffer, REPAIRED xml_buffer, RoofNames xml_buffer, SUUNNITELMA_ALUE xml_buffer, TILA xml_buffer, TILA_KOODI xml_buffer, Tilavuus xml_buffer, TYYPPI xml_buffer, UUID xml_buffer, Valmistunut xml_buffer, VTJ_PRT xml_buffer
    -> FeatureMerger_2 [REQUESTOR]
FeatureMerger_2
    ATTR_ACCUM_MODE = Merge Supplier
    ATTR_CONFLICT_RES = Use Requestor
    CLEANING_TOLERANCE = Automatic
    CONNECT_Z_MODE = Extend
    GEOM_TYPE = Build Polygons
    IGNORE_NULLS = No
    JOIN_KEYS = @Value(gml_id) @Value(gml_id) AUTO
    MERGE_TYPE = Attributes Only
    PROCESS_DUPS = YES
    REJECT_NULL_MISSING_KEYS = No
    SUPPLIERS_FIRST = No
    MERGED -> Building (writer CITYGML_2)
    MERGED -> Building (writer CESIUM3DTILES_1)
    MERGED -> Building (writer POSTGRES_4)
    UNMERGED_REQUESTOR -> Building (writer CITYGML_2)
    UNMERGED_REQUESTOR -> Building (writer CESIUM3DTILES_1)
    UNMERGED_REQUESTOR -> Building (writer POSTGRES_4)
Building (writer CITYGML_2)
    attributes: BREC_RoofNames xml_buffer, Cel xml_buffer, BuildingHeightNN xml_buffer, C_KAYTTARK xml_buffer, citygml_address{}.xlink_href xml_buffer, citygml_bounded_by{}.xlink_href xml_buffer, citygml_class xml_buffer, citygml_class_codeSpace xml_buffer, citygml_consists_of_building_part{}.xlink_href xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_interior_building_installation{}.xlink_href xml_buffer, citygml_interior_room{}.xlink_href xml_buffer, citygml_level_of_detail{} xml_buffer, citygml_measured_height xml_real64, citygml_measured_height_units xml_buffer, citygml_outer_building_installation{}.xlink_href xml_buffer, citygml_relative_to_terrain xml_char(33), citygml_relative_to_water xml_char(38), citygml_roof_type xml_buffer, citygml_roof_type_codeSpace xml_buffer, citygml_storey_heights_above_ground xml_buffer, citygml_storey_heights_above_ground_units xml_buffer, citygml_storey_heights_below_ground xml_buffer, citygml_storey_heights_below_ground_units xml_buffer,
      citygml_storeys_above_ground xml_uint64, citygml_storeys_below_ground xml_uint64, citygml_target_uri xml_buffer, citygml_terminationDate xml_date, citygml_usage{} xml_buffer, citygml_usage{}.codeSpace xml_buffer, citygml_year_of_construction xml_buffer, citygml_year_of_demolition xml_buffer, CODE xml_buffer, externalReference{}.externalObject.name xml_xml, externalReference{}.externalObject.uri xml_xml, externalReference{}.informationSystem xml_xml, gml_description xml_buffer, gml_name xml_buffer, GroundLevel xml_buffer, HighestRoof xml_buffer, I_KEROSAL xml_buffer, I_KERRLKM xml_buffer, ID xml_buffer, Katuosoite xml_buffer, Kayttotarkoitus xml_buffer, Kerroksia xml_buffer, Kerrosala xml_buffer, KG_KRAKENN xml_buffer, Kokonaisala xml_buffer, LowestRoof xml_buffer, Rakennuksen_tila xml_buffer, Rakennusaine xml_buffer, Rakennustunnus__RATU_ xml_buffer, Rakennustunnus__VTJ-PRT_ xml_buffer,
      RATU xml_buffer, REPAIRED xml_buffer, RoofNames xml_buffer, SUUNNITELMA_ALUE xml_buffer, TILA xml_buffer, TILA_KOODI xml_buffer, Tilavuus xml_buffer, TYYPPI xml_buffer, UUID xml_buffer, Valmistunut xml_buffer, VTJ_PRT xml_buffer, resulttime xml_char(20), datastream_id xml_int64, featureofintrest_link xml_buffer, bel_spl xml_buffer, v xml_buffer, w xml_buffer, j xml_buffer, a xml_buffer
Building (writer POSTGRES_4)
    attributes: gml_id xml, gml_parent_id xml, citygml_target_uri xml, citygml_feature_role xml, citygml_feature_role_attr_name xml, citygml_feature_role_attr_val xml, gml_description xml, gml_name xml, citygml_creationdate xml, citygml_terminationdate xml, externalreference{}_externalobject_name xml, externalreference{}_externalobject_uri xml, externalreference{}_informationsystem xml, citygml_generalizes_to{}_xlink_href xml, citygml_relative_to_terrain xml, citygml_relative_to_water xml, citygml_class xml, citygml_class_codespace xml, citygml_function{} xml, citygml_function{}_codespace xml, citygml_usage{} xml, citygml_usage{}_codespace xml, citygml_year_of_construction xml, citygml_year_of_demolition xml, citygml_roof_type xml, citygml_roof_type_codespace xml, citygml_measured_height xml, citygml_measured_height_units xml, citygml_storeys_above_ground xml, citygml_storeys_below_ground xml,
      citygml_storey_heights_above_ground xml, citygml_storey_heights_above_ground_units xml, citygml_storey_heights_below_ground xml, citygml_storey_heights_below_ground_units xml, citygml_outer_building_installation{}_xlink_href xml, citygml_interior_building_installation{}_xlink_href xml, citygml_bounded_by{}_xlink_href xml, citygml_level_of_detail{} xml, citygml_interior_room{}_xlink_href xml, citygml_consists_of_building_part{}_xlink_href xml, citygml_address{}_xlink_href xml, brec_buildingheightnn xml, brec_roofnames xml, buildingheightnn xml, code xml, c_kayttark xml, groundlevel xml, highestroof xml, id xml, i_kerosal xml, i_kerrlkm xml, kg_krakenn xml, katuosoite xml, kayttotarkoitus xml, kerroksia xml, kerrosala xml, kokonaisala xml, lowestroof xml, ratu xml, repaired xml,
      rakennuksen_tila xml, rakennusaine xml, rakennustunnus__ratu_ xml, rakennustunnus__vtj_prt_ xml, roofnames xml, suunnitelma_alue xml, tila xml, tila_koodi xml, tyyppi xml, tilavuus xml, uuid xml, vtj_prt xml, valmistunut xml, bel_spl xml, w xml, v xml, a xml, j xml
Building (writer CESIUM3DTILES_1)
    attributes: BREC_BuildingHeightNN string, BREC_RoofNames string, BuildingHeightNN string, C_KAYTTARK string, citygml_address{}.xlink_href string, citygml_bounded_by{}.xlink_href string, citygml_class string, citygml_class_codeSpace string, citygml_consists_of_building_part{}.xlink_href string, citygml_creationDate string, citygml_feature_role string, citygml_feature_role_attr_name string, citygml_feature_role_attr_val string, citygml_function{} string, citygml_function{}.codeSpace string, citygml_generalizes_to{}.xlink_href string, citygml_interior_building_installation{}.xlink_href string, citygml_interior_room{}.xlink_href string, citygml_level_of_detail{} string, citygml_measured_height float, citygml_measured_height_units string, citygml_outer_building_installation{}.xlink_href string, citygml_relative_to_terrain string, citygml_relative_to_water string, citygml_roof_type string, citygml_roof_type_codeSpace string, citygml_storey_heights_above_ground string, citygml_storey_heights_above_ground_units string, citygml_storey_heights_below_ground string, citygml_storey_heights_below_ground_units string,
      citygml_storeys_above_ground string, citygml_storeys_below_ground string, citygml_target_uri string, citygml_terminationDate string, citygml_usage{} string, citygml_usage{}.codeSpace string, citygml_year_of_construction string, citygml_year_of_demolition string, CODE string, externalReference{}.externalObject.name string, externalReference{}.externalObject.uri string, externalReference{}.informationSystem string, gml_description string, gml_name string, GroundLevel string, HighestRoof string, I_KEROSAL string, I_KERRLKM string, ID string, Katuosoite string, Kayttotarkoitus string, Kerroksia string, Kerrosala string, KG_KRAKENN string, Kokonaisala string, LowestRoof string, Rakennuksen_tila string, Rakennusaine string, Rakennustunnus_(RATU) string, Rakennustunnus_(VTJ-PRT) string,
      RATU string, REPAIRED string, RoofNames string, SUUNNITELMA_ALUE string, TILA string, TILA_KOODI string, Tilavuus string, TYYPPI string, UUID string, Valmistunut string, VTJ_PRT string, gml_id string, gml_parent_id string, bel_spl string, v string, w string, j string, a string
AzureBlobStorageConnector
    CREDENTIAL_SOURCE = Web Connection
    OPERATION_TYPE = List
    PARAMETER_SETUP = _FME_AZURE_CONTAINER]]_FME_FILES]/]_FME_INCLUDE_SUBFOLDERS]No]_FME_ATTRIBUTES_TO_ADD]_url _full_path _name]FME_CONTROLLER_QUERY_FILE]azureblobstorageconnector_deps/List.fme
WallSurface (reader POSTGRES_3)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, polyareaabs text, polyarearel text, zmax text, zmaxasl text, zmin text, zminasl text
    -> WallSurface (writer POSTGRES_4)
    -> WallSurface (writer CITYGML_3)
WallSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
WallSurface (writer POSTGRES_4)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, polyareaabs text, polyarearel text, zmax text, zmaxasl text, zmin text, zminasl text
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> Address (writer CITYGML_2)
Address (writer CITYGML_2)
    attributes: citygml_target_uri xml_buffer, citygml_feature_role xml_buffer, citygml_feature_role_attr_name xml_buffer, citygml_feature_role_attr_val xml_buffer, gml_description xml_buffer, gml_name xml_buffer, citygml_address xml_xml
CityModel (reader CITYGML_1)
    attributes: citygml_target_uri xml_buffer, gml_description xml_buffer, gml_name xml_buffer, citygml_city_object_member{}.xlink_href xml_buffer, gml_feature_member{}.xlink_href xml_buffer
    -> CityModel (writer CITYGML_2)
CityModel (writer CITYGML_2)
    attributes: citygml_target_uri xml_buffer, gml_description xml_buffer, gml_name xml_buffer, citygml_city_object_member{}.xlink_href xml_buffer, citygml_appearance_member{}.xlink_href xml_buffer, gml_feature_member{}.xlink_href xml_buffer
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, ZMin xml_buffer, ZMinASL xml_buffer
    -> GroundSurface (writer CITYGML_2)
GroundSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, Area xml_buffer, FaceUUID xml_buffer, ZMin xml_buffer, ZMinASL xml_buffer
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
    -> RoofSurface (writer CITYGML_2)
RoofSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Area xml_buffer, FaceUUID xml_buffer, PolyAreaAbs xml_buffer, PolyAreaRel xml_buffer, ZMax xml_buffer, ZMaxASL xml_buffer, ZMin xml_buffer, ZMinASL xml_buffer
    -> WallSurface (writer CITYGML_2)
WallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, Area xml_buffer, FaceUUID xml_buffer, PolyAreaAbs xml_buffer, PolyAreaRel xml_buffer, ZMax xml_buffer, ZMaxASL xml_buffer, ZMin xml_buffer, ZMinASL xml_buffer
Address (reader POSTGRES_3)
    attributes: gml_id text, gml_parent_id text, citygml_target_uri text, citygml_feature_role text, citygml_feature_role_attr_name text, citygml_feature_role_attr_val text, gml_description text, gml_name text, citygml_address xml
    -> Address (writer POSTGRES_4)
    -> Address (writer CITYGML_3)
Address (writer CITYGML_3)
    attributes: citygml_target_uri xml_buffer, citygml_feature_role xml_buffer, citygml_feature_role_attr_name xml_buffer, citygml_feature_role_attr_val xml_buffer, gml_description xml_buffer, gml_name xml_buffer, citygml_address xml_xml
Address (writer POSTGRES_4)
    attributes: gml_id text, gml_parent_id text, citygml_target_uri text, citygml_feature_role text, citygml_feature_role_attr_name text, citygml_feature_role_attr_val text, gml_description text, gml_name text, citygml_address xml
RoofSurface (reader POSTGRES_3)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, rooforientation text, roofpitch text, zmax text, zmaxasl text, zmin text, zminasl text
    -> RoofSurface (writer CITYGML_3)
RoofSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
CityModel (reader POSTGRES_3)
    attributes: gml_id text, citygml_target_uri text, gml_description text, gml_name text, citygml_city_object_member{}_xlink_href text, gml_feature_member{}_xlink_href text
    -> CityModel (writer POSTGRES_4)
    -> CityModel (writer CITYGML_3)
CityModel (writer CITYGML_3)
    attributes: citygml_target_uri xml_buffer, gml_description xml_buffer, gml_name xml_buffer, citygml_city_object_member{}.xlink_href xml_buffer, citygml_appearance_member{}.xlink_href xml_buffer, gml_feature_member{}.xlink_href xml_buffer
CityModel (writer POSTGRES_4)
    attributes: gml_id text, citygml_target_uri text, gml_description text, gml_name text, citygml_city_object_member{}_xlink_href text, gml_feature_member{}_xlink_href text
GroundSurface (reader POSTGRES_3)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, zmin text, zminasl text
    -> GroundSurface (writer POSTGRES_4)
    -> GroundSurface (writer CITYGML_3)
GroundSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
GroundSurface (writer POSTGRES_4)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_level_of_detail{} text, citygml_opening{}_xlink_href text, area text, faceuuid text, zmin text, zminasl text

Bookmark: Reader Feature Types
observation (reader POSTGRES_1)
    attributes: id int8,PrimaryKey, phenomenontime_begin timestamp, phenomenontime_end timestamp, resulttime timestamp, result text, resultquality json, validtime_begin timestamp, validtime_end timestamp, parameters json, datastream_id int8, featureofintrest_link text
    -> Observation_tester

Bookmark: Writer Feature Types
public.observation (writer JSON_1)
    attributes: unitofmeasurement string, gml_id string, id int, result string, datastream_id int, resulttime float, phenomenontime_begin float, featureofintrest_link string
