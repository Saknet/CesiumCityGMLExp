FME workspace citygml2cesium3dtilesKalasatama.fmw

Parameters:
- SourceDataset_CITYGML = C:\Users\Demo\CesiumCityGMLExp\FME_data_out\kalasatamapart.gml   # Source CityGML File(s)
- DestDataset_CESIUM3DTILES = C:\Users\Demo\CesiumCityGMLExp\public   # Destination Cesium 3D Tiles Folder
- DestDataset_CESIUM3DTILES_3 = C:\Users\Demo\CesiumCityGMLExp\FME_data_out\Test_Tiles   # Destination Cesium 3D Tiles Folder
- SourceDataset_POSTGRES = 3dcitydblocal   # Connection
- DestDataset_JSON = C:\Users\Demo\CesiumCityGMLExp\FME_data_out\Test_Tiles\test2.json   # Destination JSON (JavaScript Object Notation) File
- DestDataset_JSON_3 = C:\Users\Demo\CesiumCityGMLExp\FME_data_out\Test_Tiles\test1.json   # Destination JSON (JavaScript Object Notation) File

Readers:
- CITYGML_1: CITYGML from $(SourceDataset_CITYGML)
- POSTGRES_1: POSTGRES from $(SourceDataset_POSTGRES)

Writers:
- CESIUM3DTILES_1: CESIUM3DTILES to $(DestDataset_CESIUM3DTILES)
- CESIUM3DTILES_2: CESIUM3DTILES to $(DestDataset_CESIUM3DTILES_3)
- JSON_1: JSON to $(DestDataset_JSON)
- JSON_2: JSON to $(DestDataset_JSON_3)

Building (writer JSON_2)
    attributes: gml_id string, gml_parent_id string, citygml_target_uri string, citygml_feature_role string, citygml_feature_role_attr_name string, citygml_feature_role_attr_val string, gml_description string, gml_name string, citygml_creationDate string, citygml_terminationDate string, externalReference{}.externalObject.name string, externalReference{}.externalObject.uri string, externalReference{}.informationSystem string, citygml_generalizes_to{}.xlink_href string, citygml_relative_to_terrain string, citygml_relative_to_water string, citygml_appearance{}.xlink_href string, citygml_class string, citygml_class_codeSpace string, citygml_function{} string, citygml_function{}.codeSpace string, citygml_usage{} string, citygml_usage{}.codeSpace string, citygml_year_of_construction string, citygml_year_of_demolition string, citygml_roof_type string, citygml_roof_type_codeSpace string, citygml_measured_height float, citygml_measured_height_units string, citygml_storeys_above_ground string,
      citygml_storeys_below_ground string, citygml_storey_heights_above_ground string, citygml_storey_heights_above_ground_units string, citygml_storey_heights_below_ground string, citygml_storey_heights_below_ground_units string, citygml_outer_building_installation{}.xlink_href string, citygml_interior_building_installation{}.xlink_href string, citygml_bounded_by{}.xlink_href string, citygml_level_of_detail{} string, citygml_interior_room{}.xlink_href string, citygml_consists_of_building_part{}.xlink_href string, citygml_address{}.xlink_href string, BREC_BuildingHeightNN string, BREC_RoofNames string, BuildingHeightNN string, CODE string, C_KAYTTARK string, GroundLevel string, HighestRoof string, ID string, I_KEROSAL string, I_KERRLKM string, KG_KRAKENN string, Katuosoite string, Kayttotarkoitus string, Kerroksia string, Kerrosala string, Kokonaisala string, LowestRoof string, RATU string,
      REPAIRED string, Rakennuksen_tila string, Rakennusaine string, RoofNames string, SUUNNITELMA_ALUE string, TILA string, TILA_KOODI string, TYYPPI string, Tilavuus string, UUID string, VTJ_PRT string, Valmistunut string, result string
Building (reader POSTGRES_1)
    attributes: gml_id text, gml_parent_id text, citygml_target_uri text, citygml_feature_role text, citygml_feature_role_attr_name text, citygml_feature_role_attr_val text, gml_description text, gml_name text, citygml_creationdate text, citygml_terminationdate text, externalreference{}_externalobject_name xml, externalreference{}_externalobject_uri xml, externalreference{}_informationsystem xml, citygml_generalizes_to{}_xlink_href text, citygml_relative_to_terrain varchar(33), citygml_relative_to_water varchar(38), citygml_class text, citygml_class_codespace text, citygml_function{} text, citygml_function{}_codespace text, citygml_usage{} text, citygml_usage{}_codespace text, citygml_year_of_construction text, citygml_year_of_demolition text, citygml_roof_type text, citygml_roof_type_codespace text, citygml_measured_height float8, citygml_measured_height_units text, citygml_storeys_above_ground numeric(20,0), citygml_storeys_below_ground numeric(20,0),
      citygml_storey_heights_above_ground text, citygml_storey_heights_above_ground_units text, citygml_storey_heights_below_ground text, citygml_storey_heights_below_ground_units text, citygml_outer_building_installation{}_xlink_href text, citygml_interior_building_installation{}_xlink_href text, citygml_bounded_by{}_xlink_href text, citygml_level_of_detail{} text, citygml_interior_room{}_xlink_href text, citygml_consists_of_building_part{}_xlink_href text, citygml_address{}_xlink_href text, brec_buildingheightnn text, brec_roofnames text, buildingheightnn text, code text, c_kayttark text, groundlevel text, highestroof text, id text, i_kerosal text, i_kerrlkm text, kg_krakenn text, katuosoite text, kayttotarkoitus text, kerroksia text, kerrosala text, kokonaisala text, lowestroof text, ratu text, repaired text,
      rakennuksen_tila text, rakennusaine text, rakennustunnus__ratu_ text, rakennustunnus__vtj_prt_ text, roofnames text, suunnitelma_alue text, tila text, tila_koodi text, tyyppi text, tilavuus text, uuid text, vtj_prt text, valmistunut text, bel_spl text, v text, w text, j text, a text
    -> Building (writer CESIUM3DTILES_2) [off]
    -> Building (writer JSON_1)
Building (writer CESIUM3DTILES_2)
    attributes: gml_id string, gml_parent_id string, citygml_target_uri string, citygml_feature_role string, citygml_feature_role_attr_name string, citygml_feature_role_attr_val string, gml_description string, gml_name string, citygml_creationDate string, citygml_terminationDate string, externalReference{}.externalObject.name string, externalReference{}.externalObject.uri string, externalReference{}.informationSystem string, citygml_generalizes_to{}.xlink_href string, citygml_relative_to_terrain string, citygml_relative_to_water string, citygml_appearance{}.xlink_href string, citygml_class string, citygml_class_codeSpace string, citygml_function{} string, citygml_function{}.codeSpace string, citygml_usage{} string, citygml_usage{}.codeSpace string, citygml_year_of_construction string, citygml_year_of_demolition string, citygml_roof_type string, citygml_roof_type_codeSpace string, citygml_measured_height float, citygml_measured_height_units string, citygml_storeys_above_ground string,
      citygml_storeys_below_ground string, citygml_storey_heights_above_ground string, citygml_storey_heights_above_ground_units string, citygml_storey_heights_below_ground string, citygml_storey_heights_below_ground_units string, citygml_outer_building_installation{}.xlink_href string, citygml_interior_building_installation{}.xlink_href string, citygml_bounded_by{}.xlink_href string, citygml_level_of_detail{} string, citygml_interior_room{}.xlink_href string, citygml_consists_of_building_part{}.xlink_href string, citygml_address{}.xlink_href string, BREC_BuildingHeightNN string, BREC_RoofNames string, BuildingHeightNN string, CODE string, C_KAYTTARK string, GroundLevel string, HighestRoof string, ID string, I_KEROSAL string, I_KERRLKM string, KG_KRAKENN string, Katuosoite string, Kayttotarkoitus string, Kerroksia string, Kerrosala string, Kokonaisala string, LowestRoof string, RATU string,
      REPAIRED string, Rakennuksen_tila string, Rakennusaine string, RoofNames string, SUUNNITELMA_ALUE string, TILA string, TILA_KOODI string, TYYPPI string, Tilavuus string, UUID string, VTJ_PRT string, Valmistunut string, bel_spl string, a string, j string, v string, w string
Building (writer JSON_1)
    attributes: gml_id string, gml_parent_id string, citygml_target_uri string, citygml_feature_role string, citygml_feature_role_attr_name string, citygml_feature_role_attr_val string, gml_description string, gml_name string, citygml_creationDate string, citygml_terminationDate string, externalReference{}.externalObject.name string, externalReference{}.externalObject.uri string, externalReference{}.informationSystem string, citygml_generalizes_to{}.xlink_href string, citygml_relative_to_terrain string, citygml_relative_to_water string, citygml_appearance{}.xlink_href string, citygml_class string, citygml_class_codeSpace string, citygml_function{} string, citygml_function{}.codeSpace string, citygml_usage{} string, citygml_usage{}.codeSpace string, citygml_year_of_construction string, citygml_year_of_demolition string, citygml_roof_type string, citygml_roof_type_codeSpace string, citygml_measured_height float, citygml_measured_height_units string, citygml_storeys_above_ground string,
      citygml_storeys_below_ground string, citygml_storey_heights_above_ground string, citygml_storey_heights_above_ground_units string, citygml_storey_heights_below_ground string, citygml_storey_heights_below_ground_units string, citygml_outer_building_installation{}.xlink_href string, citygml_interior_building_installation{}.xlink_href string, citygml_bounded_by{}.xlink_href string, citygml_level_of_detail{} string, citygml_interior_room{}.xlink_href string, citygml_consists_of_building_part{}.xlink_href string, citygml_address{}.xlink_href string, BREC_BuildingHeightNN string, BREC_RoofNames string, BuildingHeightNN string, CODE string, C_KAYTTARK string, GroundLevel string, HighestRoof string, ID string, I_KEROSAL string, I_KERRLKM string, KG_KRAKENN string, Katuosoite string, Kayttotarkoitus string, Kerroksia string, Kerrosala string, Kokonaisala string, LowestRoof string, RATU string,
      REPAIRED string, Rakennuksen_tila string, Rakennusaine string, RoofNames string, SUUNNITELMA_ALUE string, TILA string, TILA_KOODI string, TYYPPI string, Tilavuus string, UUID string, VTJ_PRT string, Valmistunut string, result string

Bookmark: Reader Feature Types
WallSurface (reader CITYGML_1)
    attributes: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
RoofSurface (reader CITYGML_1)
    attributes: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
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, Area xml_buffer, FaceUUID xml_buffer, ZMin xml_buffer, ZMinASL xml_buffer
    -> CityModel (writer CESIUM3DTILES_1)
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> CityModel (writer CESIUM3DTILES_1)
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, BREC_BuildingHeightNN xml_buffer, BREC_RoofNames xml_buffer, BuildingHeightNN xml_buffer, CODE xml_buffer, C_KAYTTARK xml_buffer, GroundLevel xml_buffer, HighestRoof xml_buffer, ID xml_buffer, I_KEROSAL xml_buffer, I_KERRLKM xml_buffer, KG_KRAKENN xml_buffer, Katuosoite xml_buffer, Kayttotarkoitus xml_buffer, Kerroksia xml_buffer, Kerrosala xml_buffer, Kokonaisala xml_buffer, LowestRoof xml_buffer, RATU xml_buffer, REPAIRED xml_buffer, Rakennuksen_tila xml_buffer,
      Rakennusaine xml_buffer, RoofNames xml_buffer, SUUNNITELMA_ALUE xml_buffer, TILA xml_buffer, TILA_KOODI xml_buffer, TYYPPI xml_buffer, Tilavuus xml_buffer, UUID xml_buffer, VTJ_PRT xml_buffer, Valmistunut xml_buffer, result xml_buffer
    -> Building (writer CESIUM3DTILES_2)
    -> Building (writer CESIUM3DTILES_1)
    -> Building (writer JSON_2)
Address (reader CITYGML_1)
    attributes: citygml_target_uri xml_buffer, citygml_feature_role xml_buffer, citygml_feature_role_attr_name xml_buffer, citygml_feature_role_attr_val xml_buffer, gml_description xml_buffer, gml_name xml_buffer, citygml_address xml_xml

Bookmark: Writer Feature Types
CityModel (writer CESIUM3DTILES_1)
    attributes: gml_id string, citygml_target_uri string, gml_description string, gml_name string, citygml_city_object_member{}.xlink_href string, citygml_appearance_member{}.xlink_href string, gml_feature_member{}.xlink_href string
Building (writer CESIUM3DTILES_1)
    attributes: gml_id string, gml_parent_id string, citygml_target_uri string, citygml_feature_role string, citygml_feature_role_attr_name string, citygml_feature_role_attr_val string, gml_description string, gml_name string, citygml_creationDate string, citygml_terminationDate string, externalReference{}.externalObject.name string, externalReference{}.externalObject.uri string, externalReference{}.informationSystem string, citygml_generalizes_to{}.xlink_href string, citygml_relative_to_terrain string, citygml_relative_to_water string, citygml_appearance{}.xlink_href string, citygml_class string, citygml_class_codeSpace string, citygml_function{} string, citygml_function{}.codeSpace string, citygml_usage{} string, citygml_usage{}.codeSpace string, citygml_year_of_construction string, citygml_year_of_demolition string, citygml_roof_type string, citygml_roof_type_codeSpace string, citygml_measured_height float, citygml_measured_height_units string, citygml_storeys_above_ground string,
      citygml_storeys_below_ground string, citygml_storey_heights_above_ground string, citygml_storey_heights_above_ground_units string, citygml_storey_heights_below_ground string, citygml_storey_heights_below_ground_units string, citygml_outer_building_installation{}.xlink_href string, citygml_interior_building_installation{}.xlink_href string, citygml_bounded_by{}.xlink_href string, citygml_level_of_detail{} string, citygml_interior_room{}.xlink_href string, citygml_consists_of_building_part{}.xlink_href string, citygml_address{}.xlink_href string, BREC_BuildingHeightNN string, BREC_RoofNames string, BuildingHeightNN string, CODE string, C_KAYTTARK string, GroundLevel string, HighestRoof string, ID string, I_KEROSAL string, I_KERRLKM string, KG_KRAKENN string, Katuosoite string, Kayttotarkoitus string, Kerroksia string, Kerrosala string, Kokonaisala string, LowestRoof string, RATU string,
      REPAIRED string, Rakennuksen_tila string, Rakennusaine string, RoofNames string, SUUNNITELMA_ALUE string, TILA string, TILA_KOODI string, TYYPPI string, Tilavuus string, UUID string, VTJ_PRT string, Valmistunut string, result string, a string, bel_spl string, j string, v string, w string
WallSurface (writer CESIUM3DTILES_1)
    attributes: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
RoofSurface (writer CESIUM3DTILES_1)
    attributes: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
GroundSurface (writer CESIUM3DTILES_1)
    attributes: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
Address (writer CESIUM3DTILES_1)
    attributes: gml_id string, gml_parent_id string, citygml_target_uri string, citygml_feature_role string, citygml_feature_role_attr_name string, citygml_feature_role_attr_val string, gml_description string, gml_name string, citygml_address string
